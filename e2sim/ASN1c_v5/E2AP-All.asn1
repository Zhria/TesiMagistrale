-- ASN1START
-- **************************************************************
--
-- Common definitions
-- Derived from 3GPP 38.413 (NGAP)
--
-- **************************************************************
E2AP-CommonDataTypes { iso(1) identified-organization(3) dod(6) internet(1) private(4) enterprise(1) 53148 e2(1) version2 (2) e2ap(1) e2ap-CommonDataTypes (3) }

DEFINITIONS AUTOMATIC TAGS ::=
BEGIN
Criticality ::= ENUMERATED { reject, ignore, notify }
Presence ::= ENUMERATED { optional, conditional, mandatory }
ProcedureCode ::= INTEGER (0..255)
ProtocolIE-ID ::= INTEGER (0..65535)
TriggeringMessage ::= ENUMERATED { initiating-message, successful-outcome, unsuccessfull-outcome }
END
-- ASN1STOP-- ASN1START
-- **************************************************************
--
-- Constant definitions
--
-- **************************************************************
E2AP-Constants {
iso(1) identified-organization(3) dod(6) internet(1) private(4) enterprise(1) 53148 e2(1) version2 (2)
e2ap(1) e2ap-Constants (4) }
DEFINITIONS AUTOMATIC TAGS ::=
BEGIN
IMPORTS
ProcedureCode,
ProtocolIE-ID
FROM E2AP-CommonDataTypes;
-- **************************************************************
--
-- Elementary Procedures
--
-- **************************************************************
id-E2setup ProcedureCode ::= 1
id-ErrorIndication ProcedureCode ::= 2
id-Reset ProcedureCode ::= 3
id-RICcontrol ProcedureCode ::= 4
id-RICindication ProcedureCode ::= 5
id-RICserviceQuery ProcedureCode ::= 6
id-RICserviceUpdate ProcedureCode ::= 7
id-RICsubscription ProcedureCode ::= 8
id-RICsubscriptionDelete ProcedureCode ::= 9
id-E2nodeConfigurationUpdate ProcedureCode ::= 10
id-E2connectionUpdate ProcedureCode ::= 11
id-RICsubscriptionDeleteRequired ProcedureCode ::= 12
id-E2removal ProcedureCode ::= 13
id-RICsubscriptionModification ProcedureCode ::= 14
id-RICsubscriptionModificationRequired ProcedureCode ::= 15
id-RICquery ProcedureCode ::= 16
id-RICsubscriptionAudit ProcedureCode ::= 17
id-RICserviceLoadStatus ProcedureCode ::= 18
id-RICserviceLoadUpdate ProcedureCode ::= 19
id-RICsubscriptionStateControl ProcedureCode ::= 20
id-RICassistance ProcedureCode ::= 21
id-RICassistanceIndication ProcedureCode ::= 22
id-RICassistanceHalt ProcedureCode ::= 23
-- **************************************************************
--
-- Extension constants
--
-- **************************************************************
maxProtocolIEs INTEGER ::= 65535
-- **************************************************************
--
-- Lists
--
-- **************************************************************
maxnoofErrors INTEGER ::= 256
maxofE2nodeComponents INTEGER ::= 1024
maxofRANfunctionID INTEGER ::= 256
maxofRICactionID INTEGER ::= 16
maxofTNLA INTEGER ::= 32
maxofRICrequestID INTEGER ::= 1024
maxofRICsubscriptions INTEGER ::= 2147483647
-- **************************************************************
--
-- IEs
--
-- **************************************************************
id-Cause ProtocolIE-ID ::= 1
id-CriticalityDiagnostics ProtocolIE-ID ::= 2
id-GlobalE2node-ID ProtocolIE-ID ::= 3
id-GlobalRIC-ID ProtocolIE-ID ::= 4
id-RANfunctionID ProtocolIE-ID ::= 5
id-RANfunctionID-Item ProtocolIE-ID ::= 6
id-RANfunctionIEcause-Item ProtocolIE-ID ::= 7
id-RANfunction-Item ProtocolIE-ID ::= 8
id-RANfunctionsAccepted ProtocolIE-ID ::= 9
id-RANfunctionsAdded ProtocolIE-ID ::= 10
id-RANfunctionsDeleted ProtocolIE-ID ::= 11
id-RANfunctionsModified ProtocolIE-ID ::= 12
id-RANfunctionsRejected ProtocolIE-ID ::= 13
id-RICaction-Admitted-Item ProtocolIE-ID ::= 14
id-RICactionID ProtocolIE-ID ::= 15
id-RICaction-NotAdmitted-Item ProtocolIE-ID ::= 16
id-RICactions-Admitted ProtocolIE-ID ::= 17
id-RICactions-NotAdmitted ProtocolIE-ID ::= 18
id-RICaction-ToBeSetup-Item ProtocolIE-ID ::= 19
id-RICcallProcessID ProtocolIE-ID ::= 20
id-RICcontrolAckRequest ProtocolIE-ID ::= 21
id-RICcontrolHeader ProtocolIE-ID ::= 22
id-RICcontrolMessage ProtocolIE-ID ::= 23
id-RICcontrolStatus ProtocolIE-ID ::= 24
id-RICindicationHeader ProtocolIE-ID ::= 25
id-RICindicationMessage ProtocolIE-ID ::= 26
id-RICindicationSN ProtocolIE-ID ::= 27
id-RICindicationType ProtocolIE-ID ::= 28
id-RICrequestID ProtocolIE-ID ::= 29
id-RICsubscriptionDetails ProtocolIE-ID ::= 30
id-TimeToWait ProtocolIE-ID ::= 31
id-RICcontrolOutcome ProtocolIE-ID ::= 32
id-E2nodeComponentConfigUpdate ProtocolIE-ID ::= 33
id-E2nodeComponentConfigUpdate-Item ProtocolIE-ID ::= 34
id-E2nodeComponentConfigUpdateAck ProtocolIE-ID ::= 35
id-E2nodeComponentConfigUpdateAck-Item ProtocolIE-ID ::= 36
id-E2connectionSetup ProtocolIE-ID ::= 39
id-E2connectionSetupFailed ProtocolIE-ID ::= 40
id-E2connectionSetupFailed-Item ProtocolIE-ID ::= 41
id-E2connectionFailed-Item ProtocolIE-ID ::= 42
id-E2connectionUpdate-Item ProtocolIE-ID ::= 43
id-E2connectionUpdateAdd ProtocolIE-ID ::= 44
id-E2connectionUpdateModify ProtocolIE-ID ::= 45
id-E2connectionUpdateRemove ProtocolIE-ID ::= 46
id-E2connectionUpdateRemove-Item ProtocolIE-ID ::= 47
id-TNLinformation ProtocolIE-ID ::= 48
id-TransactionID ProtocolIE-ID ::= 49
id-E2nodeComponentConfigAddition ProtocolIE-ID ::= 50
id-E2nodeComponentConfigAddition-Item ProtocolIE-ID ::= 51
id-E2nodeComponentConfigAdditionAck ProtocolIE-ID ::= 52
id-E2nodeComponentConfigAdditionAck-Item ProtocolIE-ID ::= 53
id-E2nodeComponentConfigRemoval ProtocolIE-ID ::= 54
id-E2nodeComponentConfigRemoval-Item ProtocolIE-ID ::= 55
id-E2nodeComponentConfigRemovalAck ProtocolIE-ID ::= 56
id-E2nodeComponentConfigRemovalAck-Item ProtocolIE-ID ::= 57
id-E2nodeTNLassociationRemoval ProtocolIE-ID ::= 58
id-E2nodeTNLassociationRemoval-Item ProtocolIE-ID ::= 59
id-RICsubscriptionToBeRemoved ProtocolIE-ID ::= 60
id-RICsubscription-withCause-Item ProtocolIE-ID ::= 61
id-RICsubscriptionStartTime ProtocolIE-ID ::= 62
id-RICsubscriptionEndTime ProtocolIE-ID ::= 63
id-RICeventTriggerDefinitionToBeModified ProtocolIE-ID ::= 64
id-RICactionsToBeRemovedForModification-List ProtocolIE-ID ::= 65
id-RICaction-ToBeRemovedForModification-Item ProtocolIE-ID ::= 66
id-RICactionsToBeModifiedForModification-List ProtocolIE-ID ::= 67
id-RICaction-ToBeModifiedForModification-Item ProtocolIE-ID ::= 68
id-RICactionsToBeAddedForModification-List ProtocolIE-ID ::= 69
id-RICaction-ToBeAddedForModification-Item ProtocolIE-ID ::= 70
id-RICactionsRemovedForModification-List ProtocolIE-ID ::= 71
id-RICaction-RemovedForModification-Item ProtocolIE-ID ::= 72
id-RICactionsFailedToBeRemovedForModification-List ProtocolIE-ID ::= 73
id-RICaction-FailedToBeRemovedForModification-Item ProtocolIE-ID ::= 74
id-RICactionsModifiedForModification-List ProtocolIE-ID ::= 75
id-RICaction-ModifiedForModification-Item ProtocolIE-ID ::= 76
id-RICactionsFailedToBeModifiedForModification-List ProtocolIE-ID ::= 77
id-RICaction-FailedToBeModifiedForModification-Item ProtocolIE-ID ::= 78
id-RICactionsAddedForModification-List ProtocolIE-ID ::= 79
id-RICaction-AddedForModification-Item ProtocolIE-ID ::= 80
id-RICactionsFailedToBeAddedForModification-List ProtocolIE-ID ::= 81
id-RICaction-FailedToBeAddedForModification-Item ProtocolIE-ID ::= 82
id-RICactionsRequiredToBeModified-List ProtocolIE-ID ::= 83
id-RICaction-RequiredToBeModified-Item ProtocolIE-ID ::= 84
id-RICactionsRequiredToBeRemoved-List ProtocolIE-ID ::= 85
id-RICaction-RequiredToBeRemoved-Item ProtocolIE-ID ::= 86
id-RICactionsConfirmedForModification-List ProtocolIE-ID ::= 87
id-RICaction-ConfirmedForModification-Item ProtocolIE-ID ::= 88
id-RICactionsRefusedToBeModified-List ProtocolIE-ID ::= 89
id-RICaction-RefusedToBeModified-Item ProtocolIE-ID ::= 90
id-RICactionsConfirmedForRemoval-List ProtocolIE-ID ::= 91
id-RICaction-ConfirmedForRemoval-Item ProtocolIE-ID ::= 92
id-RICactionsRefusedToBeRemoved-List ProtocolIE-ID ::= 93
id-RICaction-RefusedToBeRemoved-Item ProtocolIE-ID ::= 94
id-RICqueryHeader ProtocolIE-ID ::= 95
id-RICqueryDefinition ProtocolIE-ID ::= 96
id-RICqueryOutcome ProtocolIE-ID ::= 97
id-RICsubscriptionAuditFlag ProtocolIE-ID ::= 98
id-RICsubscriptionAuditList ProtocolIE-ID ::= 99
id-RICsubscriptionAudit-Item ProtocolIE-ID ::= 100
id-RICsubscriptionAuditAction-Item ProtocolIE-ID ::= 101
id-RICsubscriptionAuditConfirmedList ProtocolIE-ID ::= 102
id-RICsubscriptionAuditMissingList ProtocolIE-ID ::= 103
id-RICsubscriptionAuditUnknownList ProtocolIE-ID ::= 104
id-E2nodeLoadMeasurementID ProtocolIE-ID ::= 105
id-RANfunctionLoad-Item ProtocolIE-ID ::= 106
id-RANfunctionLoad-List ProtocolIE-ID ::= 107
id-RANfunctionLoadConfirm-Item ProtocolIE-ID ::= 108
id-RANfunctionLoadConfirm-List ProtocolIE-ID ::= 109
id-RANfunctionLoadRequest-Item ProtocolIE-ID ::= 110
id-RANfunctionLoadRequest-List ProtocolIE-ID ::= 111
id-RegistrationRequest ProtocolIE-ID ::= 112
id-ReportingPeriodicity ProtocolIE-ID ::= 113
id-RICactionLoad-Item ProtocolIE-ID ::= 114
id-RICactionLoadConfirm-Item ProtocolIE-ID ::= 115
id-RICactionLoadRequest-Item ProtocolIE-ID ::= 116
id-RICloadMeasurementID ProtocolIE-ID ::= 117
id-RICsubscriptionLoad-Item ProtocolIE-ID ::= 118
id-RICsubscriptionLoadConfirm-Item ProtocolIE-ID ::= 119
id-RICsubscriptionLoadRequest-Item ProtocolIE-ID ::= 120
id-RANfunctionStateConfirm-Item ProtocolIE-ID ::= 121
id-RANfunctionStateConfirm-List ProtocolIE-ID ::= 122
id-RANfunctionStateControl-Item ProtocolIE-ID ::= 123
id-RANfunctionStateControl-List ProtocolIE-ID ::= 124
id-RICactionList-Item ProtocolIE-ID ::= 125
id-RICsubscriptionList-Item ProtocolIE-ID ::= 126
id-RICassistanceHeader ProtocolIE-ID ::= 127
id-RICassistanceMessage ProtocolIE-ID ::= 128
id-RICassistanceOutcome ProtocolIE-ID ::= 129
id-RICassistanceSN ProtocolIE-ID ::= 130
id-RICassistanceUpdate ProtocolIE-ID ::= 131
id-RICassistanceUpdateNumber ProtocolIE-ID ::= 132
END
-- ASN1STOP-- ASN1START
-- **************************************************************
--
-- Container definitions
--
-- derived from 3GPP 38.413 (NGAP)
-- **************************************************************
E2AP-Containers {
iso(1) identified-organization(3) dod(6) internet(1) private(4) enterprise(1) 53148 e2(1) version2 (2)
e2ap(1) e2ap-Containers (5) }
DEFINITIONS AUTOMATIC TAGS ::=
BEGIN
-- **************************************************************
--
-- IE parameter types from other modules.
--
-- **************************************************************
IMPORTS
Criticality,
Presence,
ProtocolIE-ID
FROM E2AP-CommonDataTypes

maxProtocolIEs
FROM E2AP-Constants;
-- **************************************************************
--
-- Class Definition for Protocol IEs
--
-- **************************************************************
E2AP-PROTOCOL-IES ::= CLASS {
&id ProtocolIE-ID UNIQUE,
&criticality Criticality,
&Value,
&presence Presence
}
WITH SYNTAX {
ID &id
CRITICALITY &criticality
TYPE &Value
PRESENCE &presence
}
-- **************************************************************
--
-- Class Definition for Protocol IEs
--
-- **************************************************************
E2AP-PROTOCOL-IES-PAIR ::= CLASS {
&id ProtocolIE-ID UNIQUE,
&firstCriticality Criticality,
&FirstValue,
&secondCriticality Criticality,
&SecondValue,
&presence Presence
}
WITH SYNTAX {
ID &id
FIRST CRITICALITY &firstCriticality
FIRST TYPE &FirstValue
SECOND CRITICALITY &secondCriticality
SECOND TYPE &SecondValue
PRESENCE &presence
}
-- **************************************************************
--
-- Container for Protocol IEs
--
-- **************************************************************
ProtocolIE-Container {E2AP-PROTOCOL-IES : IEsSetParam} ::=
SEQUENCE (SIZE (0..maxProtocolIEs)) OF
ProtocolIE-Field {{IEsSetParam}}
ProtocolIE-SingleContainer {E2AP-PROTOCOL-IES : IEsSetParam} ::=
ProtocolIE-Field {{IEsSetParam}}
ProtocolIE-Field {E2AP-PROTOCOL-IES : IEsSetParam} ::= SEQUENCE {
id E2AP-PROTOCOL-IES.&id ({IEsSetParam}),
criticality E2AP-PROTOCOL-IES.&criticality ({IEsSetParam}{@id}),
value E2AP-PROTOCOL-IES.&Value ({IEsSetParam}{@id})
}
-- **************************************************************
--
-- Container for Protocol IE Pairs
--
-- **************************************************************
ProtocolIE-ContainerPair {E2AP-PROTOCOL-IES-PAIR : IEsSetParam} ::=
SEQUENCE (SIZE (0..maxProtocolIEs)) OF
ProtocolIE-FieldPair {{IEsSetParam}}
ProtocolIE-FieldPair {E2AP-PROTOCOL-IES-PAIR : IEsSetParam} ::= SEQUENCE {
id E2AP-PROTOCOL-IES-PAIR.&id ({IEsSetParam}),
firstCriticality E2AP-PROTOCOL-IES-PAIR.&firstCriticality ({IEsSetParam}{@id}),
firstValue E2AP-PROTOCOL-IES-PAIR.&FirstValue ({IEsSetParam}{@id}),
secondCriticality E2AP-PROTOCOL-IES-PAIR.&secondCriticality ({IEsSetParam}{@id}),
secondValue E2AP-PROTOCOL-IES-PAIR.&SecondValue ({IEsSetParam}{@id})
}
-- **************************************************************
--
-- Container Lists for Protocol IE Containers
--
-- **************************************************************
ProtocolIE-ContainerList {INTEGER : lowerBound, INTEGER : upperBound, E2AP-PROTOCOL-IES : IEsSetParam} ::=
SEQUENCE (SIZE (lowerBound..upperBound)) OF
ProtocolIE-SingleContainer {{IEsSetParam}}
ProtocolIE-ContainerPairList {INTEGER : lowerBound, INTEGER : upperBound, E2AP-PROTOCOL-IES-PAIR :
IEsSetParam} ::=
SEQUENCE (SIZE (lowerBound..upperBound)) OF
ProtocolIE-ContainerPair {{IEsSetParam}}
END
-- ASN1STOP-- ASN1START
-- **************************************************************
-- E2AP
-- Information Element Definitions
--
-- **************************************************************
E2AP-IEs {
iso(1) identified-organization(3) dod(6) internet(1) private(4) enterprise(1) 53148 e2(1) version2 (2)
e2ap(1) e2ap-IEs (2)}
DEFINITIONS AUTOMATIC TAGS ::=
BEGIN
IMPORTS
Criticality,
Presence,
ProcedureCode,
ProtocolIE-ID,
TriggeringMessage
FROM E2AP-CommonDataTypes
maxnoofErrors,
maxProtocolIEs
FROM E2AP-Constants;
-- A
-- **************************************************************
-- [New for E2AP v02.00] copied from 3GPP 38.413 (NGAP) IEs
-- **************************************************************
AMFName ::= PrintableString (SIZE(1..150, ...))
-- B
-- C
Cause ::= CHOICE {
ricRequest CauseRICrequest,
ricService CauseRICservice,
e2Node CauseE2node,
transport CauseTransport,
protocol CauseProtocol,
misc CauseMisc,
...,
serviceLayer CauseServiceLayer
}
CauseE2node ::= ENUMERATED {
e2node-component-unknown,
...
}
CauseMisc ::= ENUMERATED {
control-processing-overload,
hardware-failure,
om-intervention,
unspecified,
...
}
CauseProtocol ::= ENUMERATED {
transfer-syntax-error,
abstract-syntax-error-reject,
abstract-syntax-error-ignore-and-notify,
message-not-compatible-with-receiver-state,
semantic-error,
abstract-syntax-error-falsely-constructed-message,
unspecified,
...
}
CauseRICrequest ::= ENUMERATED {
ran-function-id-invalid,
action-not-supported,
excessive-actions,
duplicate-action,
duplicate-event-trigger,
function-resource-limit,
request-id-unknown,
inconsistent-action-subsequent-action-sequence,
control-message-invalid,
ric-call-process-id-invalid,
control-timer-expired,
control-failed-to-execute,
system-not-ready,
unspecified,
... ,
ric-subscription-end-time-expired,
ric-subscription-end-time-invalid,
duplicate-ric-request-id,
eventTriggerNotSupported,
requested-information-unavailable,
invalid-information-request
}
CauseRICservice ::= ENUMERATED{
ran-function-not-supported,
excessive-functions,
ric-resource-limit,
...
}
CauseServiceLayer ::= SEQUENCE {
serviceLayerCause ServiceLayerCause,
...
}
CauseTransport ::= ENUMERATED {
unspecified,
transport-resource-unavailable,
...
}
-- **************************************************************
-- copied from 3GPP 38.413 (NGAP) IEs
-- note: ie-Extensions removed
-- **************************************************************
CriticalityDiagnostics ::= SEQUENCE {
procedureCode ProcedureCode OPTIONAL,
triggeringMessage TriggeringMessage OPTIONAL,
procedureCriticality Criticality OPTIONAL,
ricRequestorID RICrequestID OPTIONAL,
iEsCriticalityDiagnostics CriticalityDiagnostics-IE-List OPTIONAL,
...
}
CriticalityDiagnostics-IE-List ::= SEQUENCE (SIZE(1..maxnoofErrors)) OF CriticalityDiagnostics-IE-Item
CriticalityDiagnostics-IE-Item ::= SEQUENCE {
iECriticality Criticality,
iE-ID ProtocolIE-ID,
typeOfError TypeOfError,
...
}
-- D
-- E
-- Following IE used to carry 3GPP defined SETUP and RAN Configuration messages defined in F1AP, E1AP, XnAP, etc.
E2nodeComponentConfiguration ::= SEQUENCE{
e2nodeComponentRequestPart OCTET STRING,
e2nodeComponentResponsePart OCTET STRING,
...
}
E2nodeComponentConfigurationAck ::= SEQUENCE{
updateOutcome ENUMERATED {success, failure, ...},
failureCause Cause OPTIONAL,
...
}
E2nodeComponentInterfaceType ::= ENUMERATED {ng, xn, e1, f1, w1, s1, x2,...}
E2nodeComponentID ::= CHOICE{
e2nodeComponentInterfaceTypeNG E2nodeComponentInterfaceNG,
e2nodeComponentInterfaceTypeXn E2nodeComponentInterfaceXn,
e2nodeComponentInterfaceTypeE1 E2nodeComponentInterfaceE1,
e2nodeComponentInterfaceTypeF1 E2nodeComponentInterfaceF1,
e2nodeComponentInterfaceTypeW1 E2nodeComponentInterfaceW1,
e2nodeComponentInterfaceTypeS1 E2nodeComponentInterfaceS1,
e2nodeComponentInterfaceTypeX2 E2nodeComponentInterfaceX2,
...
}
E2nodeComponentInterfaceE1 ::= SEQUENCE{
gNB-CU-UP-ID GNB-CU-UP-ID,
...
}
E2nodeComponentInterfaceF1 ::= SEQUENCE{
gNB-DU-ID GNB-DU-ID,
...
}
E2nodeComponentInterfaceNG ::= SEQUENCE{
amf-name AMFName,
...
}
E2nodeComponentInterfaceS1 ::= SEQUENCE{
mme-name MMEname,
...
}
E2nodeComponentInterfaceX2 ::= SEQUENCE{
global-eNB-ID GlobalENB-ID OPTIONAL,
global-en-gNB-ID GlobalenGNB-ID OPTIONAL,
...
}
E2nodeComponentInterfaceXn ::= SEQUENCE{
global-NG-RAN-Node-ID GlobalNG-RANNode-ID,
...
}
E2nodeComponentInterfaceW1 ::= SEQUENCE{
ng-eNB-DU-ID NGENB-DU-ID,
...
}
-- **************************************************************
-- copied from 3GPP 36.423 (X2AP) IEs
-- note: ie-Extensions removed
-- **************************************************************
ENB-ID ::= CHOICE {
macro-eNB-ID BIT STRING (SIZE (20)),
home-eNB-ID BIT STRING (SIZE (28)),
... ,
short-Macro-eNB-ID BIT STRING (SIZE(18)),
long-Macro-eNB-ID BIT STRING (SIZE(21))
}
-- **************************************************************
-- copied from 3GPP 38.423 (XnAP) IEs
-- note: choice-extension removed
-- **************************************************************
ENB-ID-Choice ::= CHOICE {
enb-ID-macro BIT STRING (SIZE(20)),
enb-ID-shortmacro BIT STRING (SIZE(18)),
enb-ID-longmacro BIT STRING (SIZE(21)),
...
}
-- **************************************************************
-- copied from 3GPP 36.423 (X2AP) IEs
-- note: ie-Extensions removed
-- Note: to avoid duplicate names with XnAP, GNB-ID renamed ENGNB-ID, GlobalGNB-ID renamed GlobalenGNB-ID
-- **************************************************************
ENGNB-ID ::= CHOICE {
gNB-ID BIT STRING (SIZE (22..32)),
...
}
-- F
-- G
GlobalE2node-ID ::= CHOICE{
gNB GlobalE2node-gNB-ID,
en-gNB GlobalE2node-en-gNB-ID,
ng-eNB GlobalE2node-ng-eNB-ID,
eNB GlobalE2node-eNB-ID,
...
}
GlobalE2node-en-gNB-ID ::= SEQUENCE{
global-en-gNB-ID GlobalenGNB-ID,
en-gNB-CU-UP-ID GNB-CU-UP-ID OPTIONAL,
en-gNB-DU-ID GNB-DU-ID OPTIONAL,
...
}
GlobalE2node-eNB-ID ::= SEQUENCE{
global-eNB-ID GlobalENB-ID,
...
}
GlobalE2node-gNB-ID ::= SEQUENCE{
global-gNB-ID GlobalgNB-ID,
global-en-gNB-ID GlobalenGNB-ID OPTIONAL,
gNB-CU-UP-ID GNB-CU-UP-ID OPTIONAL,
gNB-DU-ID GNB-DU-ID OPTIONAL,
...
}
GlobalE2node-ng-eNB-ID ::= SEQUENCE{
global-ng-eNB-ID GlobalngeNB-ID,
global-eNB-ID GlobalENB-ID OPTIONAL,
ngENB-DU-ID NGENB-DU-ID OPTIONAL,
...
}
-- **************************************************************
-- copied from 3GPP 36.423 (X2AP) IEs
-- note: ie-Extensions removed
-- **************************************************************
GlobalENB-ID ::= SEQUENCE {
pLMN-Identity PLMN-Identity,
eNB-ID ENB-ID,
...
}
-- **************************************************************
-- Note: to avoid duplicate names with XnAP, GNB-ID renamed ENGNB-ID, GlobalGNB-ID renamed GlobalenGNB-ID
-- **************************************************************
GlobalenGNB-ID ::= SEQUENCE {
pLMN-Identity PLMN-Identity,
gNB-ID ENGNB-ID,
...
}
-- **************************************************************
-- copied from 3GPP 38.423 (XnAP) IEs
-- note: choice-extension removed
-- **************************************************************
GlobalgNB-ID ::= SEQUENCE {
plmn-id PLMN-Identity,
gnb-id GNB-ID-Choice,
...
}
-- **************************************************************
-- copied from 3GPP 38.423 (XnAP) IEs
-- note: choice-extension removed
-- **************************************************************
GlobalngeNB-ID ::= SEQUENCE {
plmn-id PLMN-Identity,
enb-id ENB-ID-Choice,
...
}
-- **************************************************************
-- [NEW for E2AP v02.00] copied from 3GPP 38.423 (XnAP) IEs
-- Note: extension field removed
-- **************************************************************
GlobalNG-RANNode-ID ::= CHOICE {
gNB GlobalgNB-ID,
ng-eNB GlobalngeNB-ID,
...
}
GlobalRIC-ID ::= SEQUENCE{
pLMN-Identity PLMN-Identity,
ric-ID BIT STRING (SIZE (20)),
...
}
-- **************************************************************
-- copied from 3GPP 37.483 (E1AP) IEs
-- **************************************************************
GNB-CU-UP-ID::= INTEGER (0..68719476735)
-- **************************************************************
-- copied from 3GPP 38.473 (F1AP) IEs
-- **************************************************************
GNB-DU-ID::= INTEGER (0..68719476735)
-- **************************************************************
-- copied from 3GPP 38.423 (XnAP) IEs
-- note: choice-extension removed
-- **************************************************************
GNB-ID-Choice ::= CHOICE {
gnb-ID BIT STRING (SIZE(22..32)),
...
}
-- H
-- I
-- J
-- K
-- L
ListedRecordsOnly ::= ENUMERATED {true, ...}
LoadMeasurementID ::= INTEGER(1..4095,...)
-- M
-- **************************************************************
-- [New for E2AP v02.00] copied from 3GPP 36.413 (S1AP) IEs
-- **************************************************************
MMEname ::= PrintableString (SIZE (1..150,...))
-- N
-- **************************************************************
-- copied from 3GPP 37.473 (W1AP) IEs
-- **************************************************************
NGENB-DU-ID ::= INTEGER (0..68719476735)
-- O
-- P
-- **************************************************************
-- copied from 3GPP 36.423 (X2AP) IEs
-- **************************************************************
PLMN-Identity ::= OCTET STRING (SIZE(3))
-- Q
-- R
-- **************************************************************
-- Following IE defined in E2SM
-- **************************************************************
RANfunctionDefinition ::= OCTET STRING
RANfunctionID ::= INTEGER (0..4095)
RANfunctionOID ::= PrintableString(SIZE(1..1000,...))
RANfunctionRevision ::= INTEGER (0..4095)
RegistrationRequest ::= ENUMERATED{start, stop, add, ...}
ReportingPeriodicity ::= ENUMERATED{ms500, ms1000, ms2000, ms5000, ms10000, ...}
-- **************************************************************
-- Following IE defined in E2SM
-- **************************************************************
RICactionDefinition ::= OCTET STRING
-- new in E2AP-v03.00
RICactionExecutionOrder ::= INTEGER (0..255, ...)
RICactionID ::= INTEGER (0..255)
RICactionType ::= ENUMERATED{
report,
insert,
policy,
...
}
-- **************************************************************
-- Following IE defined in E2SM
-- **************************************************************
RICassistanceHeader ::= OCTET STRING
-- **************************************************************
-- Following IE defined in E2SM
-- **************************************************************
RICassistanceMessage ::= OCTET STRING
-- **************************************************************
-- Following IE defined in E2SM
-- ************************************************************
RICassistanceOutcome ::= OCTET STRING
RICassistanceSN ::=INTEGER (0..65535)
RICassistanceUpdate::= ENUMERATED{
true,
...
}
RICassistanceUpdateNumber ::=INTEGER (0..65535)
-- **************************************************************
-- Following IE defined in E2SM
-- **************************************************************
RICcallProcessID ::= OCTET STRING
RICcontrolAckRequest ::= ENUMERATED{
noAck,
ack,
...
}
-- **************************************************************
-- Following IE defined in E2SM
-- **************************************************************
RICcontrolHeader ::= OCTET STRING
-- **************************************************************
-- Following IE defined in E2SM
-- **************************************************************
RICcontrolMessage ::= OCTET STRING
-- **************************************************************
-- Following IE defined in E2SM
-- **************************************************************
RICcontrolOutcome ::= OCTET STRING
-- **************************************************************
-- Following IE defined in E2SM
-- **************************************************************
RICeventTriggerDefinition ::= OCTET STRING
-- **************************************************************
-- Following IE defined in E2SM
-- **************************************************************
RICindicationHeader ::= OCTET STRING
-- **************************************************************
-- Following IE defined in E2SM
-- **************************************************************
RICindicationMessage ::= OCTET STRING
RICindicationSN ::= INTEGER (0..65535)
RICindicationType ::= ENUMERATED{
report,
insert,
...
}
RICloadConfirm ::= ENUMERATED{
true,
...
}
RICloadInformation ::= SEQUENCE{
loadStatus ENUMERATED{overload, notoverload, ...} OPTIONAL,
loadEstimate INTEGER (0..100) OPTIONAL,
...
}
RICloadRequest ::= ENUMERATED{
true,
...
}
RICrequestID ::= SEQUENCE {
ricRequestorID INTEGER (0..65535),
ricInstanceID INTEGER (0..65535),
...
}
RICserviceLoadConfirm ::= SEQUENCE{
ricServiceReportLoadConfirm RICloadConfirm OPTIONAL,
ricServiceInsertLoadConfirm RICloadConfirm OPTIONAL,
ricServiceControlLoadConfirm RICloadConfirm OPTIONAL,
ricServicePolicyLoadConfirm RICloadConfirm OPTIONAL,
ricServiceQueryLoadConfirm RICloadConfirm OPTIONAL,
...
}
RICserviceLoadInformation ::= SEQUENCE{
ricServiceReportLoadInformation RICloadInformation OPTIONAL,
ricServiceInsertLoadInformation RICloadInformation OPTIONAL,
ricServiceControlLoadInformation RICloadInformation OPTIONAL,
ricServicePolicyLoadInformation RICloadInformation OPTIONAL,
ricServiceQueryLoadInformation RICloadInformation OPTIONAL,
...
}
RICserviceLoadRequest ::= SEQUENCE{
ricServiceReportLoadRequest RICloadRequest OPTIONAL,
ricServiceInsertLoadRequest RICloadRequest OPTIONAL,
ricServiceControlLoadRequest RICloadRequest OPTIONAL,
ricServicePolicyLoadRequest RICloadRequest OPTIONAL,
ricServiceQueryLoadRequest RICloadRequest OPTIONAL,
...
}
RICsubscriptionTime ::= OCTET STRING (SIZE(8))
RICsubsequentAction ::=SEQUENCE{
ricSubsequentActionType RICsubsequentActionType,
ricTimeToWait RICtimeToWait,
...
}
RICsubscriptionAuditFlag ::= SEQUENCE{
listedRecordsOnly ListedRecordsOnly OPTIONAL,
...
}
RICsubsequentActionType ::= ENUMERATED{
continue,
wait,
...
}
-- **************************************************************
-- Following IE defined in E2SM
-- **************************************************************
RICqueryHeader ::= OCTET STRING
-- **************************************************************
-- Following IE defined in E2SM
-- **************************************************************
RICqueryDefinition ::= OCTET STRING
-- **************************************************************
-- Following IE defined in E2SM
-- **************************************************************
RICqueryOutcome ::= OCTET STRING
RICtimeToWait ::= ENUMERATED{
w1ms,
w2ms,
w5ms,
w10ms,
w20ms,
w30ms,
w40ms,
w50ms,
w100ms,
w200ms,
w500ms,
w1s,
w2s,
w5s,
w10s,
w20s,
w60s,
...
}
-- S
-- **************************************************************
-- Following IE defined in E2SM
-- **************************************************************
ServiceLayerCause ::= OCTET STRING
-- T
-- **************************************************************
-- copied from 3GPP 38.413 (NGAP) IEs
-- **************************************************************
TimeToWait ::= ENUMERATED {v1s, v2s, v5s, v10s, v20s, v60s, ...}
TNLinformation ::= SEQUENCE{
tnlAddress BIT STRING (SIZE(1..160,...)),
tnlPort BIT STRING (SIZE(16)) OPTIONAL,
...
}
TNLusage ::= ENUMERATED{ric-service, support-function, both, ...}
TransactionID ::= INTEGER (0..255,...)
-- **************************************************************
-- copied from 3GPP 38.413 (NGAP) IEs
-- **************************************************************
TypeOfError ::= ENUMERATED {
not-understood,
missing,
...
}
-- U
-- V
-- W
-- X
-- Y
-- Z
END
-- ASN1STOP-- ASN1START
-- **************************************************************
--
-- PDU definitions for E2AP
-- Derived from 3GPP 38.413 (NGAP)
---- **************************************************************
E2AP-PDU-Contents {
iso(1) identified-organization(3) dod(6) internet(1) private(4) enterprise(1) 53148 e2(1) version2 (2)
e2ap(1) e2ap-PDU-Contents (1) }
DEFINITIONS AUTOMATIC TAGS ::=
BEGIN
-- **************************************************************
--
-- IE parameter types from other modules.
--
-- **************************************************************
IMPORTS
Cause,
CriticalityDiagnostics,
E2nodeComponentConfiguration,
E2nodeComponentConfigurationAck,
E2nodeComponentID,
E2nodeComponentInterfaceType,
GlobalE2node-ID,
GlobalRIC-ID,
LoadMeasurementID,
RANfunctionDefinition,
RANfunctionID,
RANfunctionOID,
RANfunctionRevision,
RegistrationRequest,
ReportingPeriodicity,
RICactionDefinition,
RICactionExecutionOrder,
RICactionID,
RICactionType,
RICassistanceHeader,
RICassistanceMessage,
RICassistanceOutcome,
RICassistanceSN,
RICassistanceUpdate,
RICassistanceUpdateNumber,
RICcallProcessID,
RICcontrolAckRequest,
RICcontrolHeader,
RICcontrolMessage,
RICcontrolOutcome,
RICeventTriggerDefinition,
RICindicationHeader,
RICindicationMessage,
RICindicationSN,
RICindicationType,
RICloadConfirm,
RICloadInformation,
RICloadRequest,
RICqueryHeader,
RICqueryDefinition,
RICqueryOutcome,
RICrequestID,
RICserviceLoadConfirm,
RICserviceLoadInformation,
RICserviceLoadRequest,
RICsubsequentAction,
RICsubscriptionTime,
RICsubscriptionAuditFlag,
RICtimeToWait,
TimeToWait,
TNLinformation,
TNLusage,
TransactionID
FROM E2AP-IEs
ProtocolIE-Container{},
ProtocolIE-ContainerList{},
ProtocolIE-SingleContainer{},
E2AP-PROTOCOL-IES,
E2AP-PROTOCOL-IES-PAIR
FROM E2AP-Containers


id-Cause,
id-CriticalityDiagnostics,
id-E2connectionSetup,
id-E2connectionSetupFailed,
id-E2connectionSetupFailed-Item,
id-E2connectionFailed-Item,
id-E2connectionUpdate-Item,
id-E2connectionUpdateAdd,
id-E2connectionUpdateModify,
id-E2connectionUpdateRemove,
id-E2connectionUpdateRemove-Item,
id-E2nodeComponentConfigAddition,
id-E2nodeComponentConfigAddition-Item,
id-E2nodeComponentConfigAdditionAck,
id-E2nodeComponentConfigAdditionAck-Item,
id-E2nodeComponentConfigRemoval,
id-E2nodeComponentConfigRemoval-Item,
id-E2nodeComponentConfigRemovalAck,
id-E2nodeComponentConfigRemovalAck-Item,
id-E2nodeComponentConfigUpdate,
id-E2nodeComponentConfigUpdate-Item,
id-E2nodeComponentConfigUpdateAck,
id-E2nodeComponentConfigUpdateAck-Item,
id-E2nodeLoadMeasurementID,
id-E2nodeTNLassociationRemoval,
id-E2nodeTNLassociationRemoval-Item,
id-GlobalE2node-ID,
id-GlobalRIC-ID,
id-RANfunctionID,
id-RANfunctionID-Item,
id-RANfunctionIEcause-Item,
id-RANfunction-Item,
id-RANfunctionLoad-Item,
id-RANfunctionLoad-List,
id-RANfunctionLoadConfirm-Item,
id-RANfunctionLoadConfirm-List,
id-RANfunctionLoadRequest-Item,
id-RANfunctionLoadRequest-List,
id-RANfunctionsAccepted,
id-RANfunctionsAdded,
id-RANfunctionsDeleted,
id-RANfunctionsModified,
id-RANfunctionsRejected,
id-RANfunctionStateConfirm-Item,
id-RANfunctionStateConfirm-List,
id-RANfunctionStateControl-Item,
id-RANfunctionStateControl-List,
id-RegistrationRequest,
id-ReportingPeriodicity,
id-RICaction-Admitted-Item,
id-RICactionID,
id-RICaction-NotAdmitted-Item,
id-RICactions-Admitted,
id-RICactions-NotAdmitted,
id-RICaction-ToBeSetup-Item,
id-RICactionsToBeRemovedForModification-List,
id-RICaction-ToBeRemovedForModification-Item,
id-RICactionsToBeModifiedForModification-List,
id-RICaction-ToBeModifiedForModification-Item,
id-RICactionsToBeAddedForModification-List,
id-RICaction-ToBeAddedForModification-Item,
id-RICactionsRemovedForModification-List,
id-RICaction-RemovedForModification-Item,
id-RICactionsFailedToBeRemovedForModification-List,
id-RICaction-FailedToBeRemovedForModification-Item,
id-RICactionsModifiedForModification-List,
id-RICaction-ModifiedForModification-Item,
id-RICactionsFailedToBeModifiedForModification-List,
id-RICaction-FailedToBeModifiedForModification-Item,
id-RICactionsAddedForModification-List,
id-RICaction-AddedForModification-Item,
id-RICactionsFailedToBeAddedForModification-List,
id-RICaction-FailedToBeAddedForModification-Item,
id-RICactionsRequiredToBeModified-List,
id-RICaction-RequiredToBeModified-Item,
id-RICactionsRequiredToBeRemoved-List,
id-RICaction-RequiredToBeRemoved-Item,
id-RICactionsConfirmedForModification-List,
id-RICaction-ConfirmedForModification-Item,
id-RICactionList-Item,
id-RICactionLoad-Item,
id-RICactionLoadConfirm-Item,
id-RICactionLoadRequest-Item,
id-RICactionsRefusedToBeModified-List,
id-RICaction-RefusedToBeModified-Item,
id-RICactionsConfirmedForRemoval-List,
id-RICaction-ConfirmedForRemoval-Item,
id-RICactionsRefusedToBeRemoved-List,
id-RICaction-RefusedToBeRemoved-Item,
id-RICassistanceHeader,
id-RICassistanceMessage,
id-RICassistanceOutcome,
id-RICassistanceSN,
id-RICassistanceUpdate,
id-RICassistanceUpdateNumber,
id-RICcallProcessID,
id-RICcontrolAckRequest,
id-RICcontrolHeader,
id-RICcontrolMessage,
id-RICcontrolOutcome,
id-RICeventTriggerDefinitionToBeModified,
id-RICindicationHeader,
id-RICindicationMessage,
id-RICindicationSN,
id-RICindicationType,
id-RICloadMeasurementID,
id-RICrequestID,
id-RICserviceQuery,
id-RICsubscriptionAuditFlag,
id-RICsubscriptionAuditList,
id-RICsubscriptionAudit-Item,
id-RICsubscriptionAuditAction-Item,
id-RICsubscriptionAuditConfirmedList,
id-RICsubscriptionAuditMissingList,
id-RICsubscriptionAuditUnknownList,
id-RICsubscriptionDetails,
id-RICsubscriptionList-Item,
id-RICsubscriptionLoad-Item,
id-RICsubscriptionLoadConfirm-Item,
id-RICsubscriptionLoadRequest-Item,
id-RICsubscriptionToBeRemoved,
id-RICsubscription-withCause-Item,
id-RICsubscriptionStartTime,
id-RICsubscriptionEndTime,
id-RICqueryHeader,
id-RICqueryDefinition,
id-RICqueryOutcome,
id-TimeToWait,
id-TNLinformation,
id-TransactionID,
maxofE2nodeComponents,
maxofRANfunctionID,
maxofRICactionID,
maxofRICrequestID,
maxofRICsubscriptions,
maxofTNLA
FROM E2AP-Constants;
-- **************************************************************
--
-- MESSAGES FOR RIC FUNCTIONAL PROCEDURES
--
-- **************************************************************
-- **************************************************************
--
-- RIC Subscription Elementary Procedure
--
-- **************************************************************
-- **************************************************************
--
-- RIC SUBSCRIPTION REQUEST
--
-- **************************************************************
RICsubscriptionRequest ::= SEQUENCE {
protocolIEs ProtocolIE-Container {{RICsubscriptionRequest-IEs}},
...
}
RICsubscriptionRequest-IEs E2AP-PROTOCOL-IES ::= {
{ ID id-RICrequestID CRITICALITY reject TYPE RICrequestID PRESENCE
mandatory}|
{ ID id-RANfunctionID CRITICALITY reject TYPE RANfunctionID PRESENCE
mandatory}|
{ ID id-RICsubscriptionDetails CRITICALITY reject TYPE RICsubscriptionDetails PRESENCE
mandatory},
...,
{ ID id-RICsubscriptionStartTime CRITICALITY reject TYPE RICsubscriptionTime PRESENCE
optional}|
{ ID id-RICsubscriptionEndTime CRITICALITY reject TYPE RICsubscriptionTime PRESENCE
optional}
}
RICsubscriptionDetails ::= SEQUENCE {
ricEventTriggerDefinition RICeventTriggerDefinition,
ricAction-ToBeSetup-List RICactions-ToBeSetup-List,
...
}
RICactions-ToBeSetup-List ::= SEQUENCE (SIZE(1..maxofRICactionID)) OF ProtocolIE-SingleContainer {
{RICaction-ToBeSetup-ItemIEs} }
RICaction-ToBeSetup-ItemIEs E2AP-PROTOCOL-IES ::= {
{ ID id-RICaction-ToBeSetup-Item CRITICALITY ignore TYPE RICaction-ToBeSetup-Item PRESENCE
mandatory },
...
}
RICaction-ToBeSetup-Item ::= SEQUENCE {
ricActionID RICactionID,
ricActionType RICactionType,
ricActionDefinition RICactionDefinition OPTIONAL,
ricSubsequentAction RICsubsequentAction OPTIONAL,
...,
ricActionExecutionOrder RICactionExecutionOrder OPTIONAL -- New in E2APv03.00
}
-- **************************************************************
--
-- RIC SUBSCRIPTION RESPONSE
--
RICsubscriptionResponse ::= SEQUENCE {
protocolIEs ProtocolIE-Container{{RICsubscriptionResponse-IEs}},
...
}
RICsubscriptionResponse-IEs E2AP-PROTOCOL-IES ::= {
{ ID id-RICrequestID CRITICALITY reject TYPE RICrequestID PRESENCE
mandatory } |
{ ID id-RANfunctionID CRITICALITY reject TYPE RANfunctionID PRESENCE
mandatory } |
{ ID id-RICactions-Admitted CRITICALITY reject TYPE RICaction-Admitted-List PRESENCE
mandatory } |
{ ID id-RICactions-NotAdmitted CRITICALITY reject TYPE RICaction-NotAdmitted-List PRESENCE
optional },
...
}
RICaction-Admitted-List ::= SEQUENCE (SIZE(1..maxofRICactionID)) OF ProtocolIE-SingleContainer{{RICaction-Admitted-ItemIEs}}
RICaction-Admitted-ItemIEs E2AP-PROTOCOL-IES ::= {
{ ID id-RICaction-Admitted-Item CRITICALITY ignore TYPE RICaction-Admitted-Item PRESENCE
mandatory },
...
}
RICaction-Admitted-Item ::= SEQUENCE {
ricActionID RICactionID,
...
}
RICaction-NotAdmitted-List ::= SEQUENCE (SIZE(0..maxofRICactionID)) OF ProtocolIE-SingleContainer {
{RICaction-NotAdmitted-ItemIEs} }
RICaction-NotAdmitted-ItemIEs E2AP-PROTOCOL-IES ::= {
{ ID id-RICaction-NotAdmitted-Item CRITICALITY ignore TYPE RICaction-NotAdmitted-Item PRESENCE
mandatory },
...
}
RICaction-NotAdmitted-Item ::= SEQUENCE {
ricActionID RICactionID,
cause Cause,
...
}
-- **************************************************************
--
-- RIC SUBSCRIPTION FAILURE
--
-- **************************************************************
RICsubscriptionFailure ::= SEQUENCE {
protocolIEs ProtocolIE-Container {{RICsubscriptionFailure-IEs}},
...
}
RICsubscriptionFailure-IEs E2AP-PROTOCOL-IES ::= {
{ ID id-RICrequestID CRITICALITY reject TYPE RICrequestID PRESENCE
mandatory }|
{ ID id-RANfunctionID CRITICALITY reject TYPE RANfunctionID PRESENCE
mandatory }|
{ ID id-Cause CRITICALITY reject TYPE Cause PRESENCE mandatory }|
{ ID id-CriticalityDiagnostics CRITICALITY ignore TYPE CriticalityDiagnostics PRESENCE
optional },
...
}
-- **************************************************************
--
-- RIC Subscription Audit Elementary Procedure
--
-- **************************************************************
-- **************************************************************
--
-- RIC SUBSCRIPTION AUDIT REQUEST
--
-- **************************************************************
RICsubscriptionAuditRequest ::= SEQUENCE {
protocolIEs ProtocolIE-Container {{RICsubscriptionAuditRequest-IEs}},
...
}
RICsubscriptionAuditRequest-IEs E2AP-PROTOCOL-IES ::= {
{ ID id-RICrequestID CRITICALITY reject TYPE RICrequestID PRESENCE
mandatory}|
{ ID id-RICsubscriptionAuditFlag CRITICALITY reject TYPE RICsubscriptionAuditFlag PRESENCE
optional}|
{ ID id-RICsubscriptionAuditList CRITICALITY reject TYPE RICsubscriptionAuditList PRESENCE
optional},
...
}
RICsubscriptionAuditList ::= SEQUENCE (SIZE(1..maxofRICsubscriptions)) OF ProtocolIE-SingleContainer {
{RICsubscriptionAudit-ItemIEs} }
RICsubscriptionAudit-ItemIEs E2AP-PROTOCOL-IES ::= {
{ ID id-RICsubscriptionAudit-Item CRITICALITY ignore TYPE RICsubscriptionAudit-Item PRESENCE
mandatory },
...
}
RICsubscriptionAudit-Item ::= SEQUENCE {
ricRequestID RICrequestID,
ranFunctionID RANfunctionID,
...
}
-- **************************************************************
--
-- RIC SUBSCRIPTION AUDIT RESPONSE
--
-- **************************************************************
RICsubscriptionAuditResponse ::= SEQUENCE {
protocolIEs ProtocolIE-Container{{RICsubscriptionAuditResponse-IEs}},
...
}
RICsubscriptionAuditResponse-IEs E2AP-PROTOCOL-IES ::= {
{ ID id-RICrequestID CRITICALITY reject TYPE RICrequestID
PRESENCE mandatory } |
{ ID id-RICsubscriptionAuditConfirmedList CRITICALITY reject TYPE
RICsubscriptionAuditActionList PRESENCE mandatory } |
{ ID id-RICsubscriptionAuditUnknownList CRITICALITY reject TYPE RICsubscriptionAuditList
PRESENCE optional } |
{ ID id-RICsubscriptionAuditMissingList CRITICALITY reject TYPE
RICsubscriptionAuditActionList PRESENCE optional },
...
}
RICsubscriptionAuditActionList ::= SEQUENCE (SIZE(1..maxofRICsubscriptions)) OF ProtocolIE-SingleContainer
{ {RICsubscriptionAuditAction-ItemIEs} }
RICsubscriptionAuditAction-ItemIEs E2AP-PROTOCOL-IES ::= {
{ ID id-RICsubscriptionAuditAction-Item CRITICALITY ignore TYPE RICsubscriptionAuditAction-Item
PRESENCE mandatory },
...
}
RICsubscriptionAuditAction-Item ::= SEQUENCE {
ricRequestID RICrequestID,
ranFunctionID RANfunctionID,
ricAction-Admitted-List RICaction-Admitted-List,
...
}
-- **************************************************************
--
-- RIC SUBSCRIPTION AUDIT FAILURE
--
-- **************************************************************
RICsubscriptionAuditFailure ::= SEQUENCE {
protocolIEs ProtocolIE-Container {{RICsubscriptionAuditFailure-IEs}},
...
}
RICsubscriptionAuditFailure-IEs E2AP-PROTOCOL-IES ::= {
{ ID id-RICrequestID CRITICALITY reject TYPE RICrequestID PRESENCE
mandatory }|
{ ID id-Cause CRITICALITY reject TYPE Cause PRESENCE
mandatory }|
{ ID id-CriticalityDiagnostics CRITICALITY ignore TYPE CriticalityDiagnostics PRESENCE
optional },
...
}
-- **************************************************************
--
-- RIC Subscription Delete Elementary Procedure
--
-- **************************************************************
-- **************************************************************
--
-- RIC SUBSCRIPTION DELETE REQUEST
--
-- **************************************************************
RICsubscriptionDeleteRequest ::= SEQUENCE {
protocolIEs ProtocolIE-Container {{RICsubscriptionDeleteRequest-IEs}},
...
}
RICsubscriptionDeleteRequest-IEs E2AP-PROTOCOL-IES ::= {
{ ID id-RICrequestID CRITICALITY reject TYPE RICrequestID PRESENCE
mandatory }|
{ ID id-RANfunctionID CRITICALITY reject TYPE RANfunctionID PRESENCE
mandatory },
...
}
-- **************************************************************
--
-- RIC SUBSCRIPTION DELETE RESPONSE
--
-- **************************************************************
RICsubscriptionDeleteResponse ::= SEQUENCE {
protocolIEs ProtocolIE-Container {{RICsubscriptionDeleteResponse-IEs}},
...
}
RICsubscriptionDeleteResponse-IEs E2AP-PROTOCOL-IES ::= {
{ ID id-RICrequestID CRITICALITY reject TYPE RICrequestID PRESENCE
mandatory }|
{ ID id-RANfunctionID CRITICALITY reject TYPE RANfunctionID PRESENCE
mandatory },
...
}
-- **************************************************************
--
-- RIC SUBSCRIPTION DELETE FAILURE
--
-- **************************************************************
RICsubscriptionDeleteFailure ::= SEQUENCE {
protocolIEs ProtocolIE-Container {{RICsubscriptionDeleteFailure-IEs}},
...
}
RICsubscriptionDeleteFailure-IEs E2AP-PROTOCOL-IES ::= {
{ ID id-RICrequestID CRITICALITY reject TYPE RICrequestID PRESENCE
mandatory }|
{ ID id-RANfunctionID CRITICALITY reject TYPE RANfunctionID PRESENCE
mandatory }|
{ ID id-Cause CRITICALITY ignore TYPE Cause PRESENCE
mandatory }|
{ ID id-CriticalityDiagnostics CRITICALITY ignore TYPE CriticalityDiagnostics PRESENCE
optional },
...
}
-- **************************************************************
--
-- RIC Subscription Delete Required Elementary Procedure
--
-- **************************************************************
-- **************************************************************
--
-- RIC SUBSCRIPTION DELETE REQUIRED
--
-- **************************************************************
RICsubscriptionDeleteRequired ::= SEQUENCE {
protocolIEs ProtocolIE-Container {{RICsubscriptionDeleteRequired-IEs}},
...
}
RICsubscriptionDeleteRequired-IEs E2AP-PROTOCOL-IES ::= {
{ ID id-RICsubscriptionToBeRemoved CRITICALITY ignore TYPE RICsubscription-List-withCause
PRESENCE mandatory },
...
}
RICsubscription-List-withCause ::= SEQUENCE (SIZE(1..maxofRICrequestID)) OF ProtocolIE-SingleContainer {
{RICsubscription-withCause-ItemIEs} }
RICsubscription-withCause-ItemIEs E2AP-PROTOCOL-IES ::= {
{ ID id-RICsubscription-withCause-Item CRITICALITY ignore TYPE RICsubscription-withCause-Item
PRESENCE mandatory },
...
}
RICsubscription-withCause-Item ::= SEQUENCE {
ricRequestID RICrequestID,
ranFunctionID RANfunctionID,
cause Cause,
...
}
-- **************************************************************
--
-- RIC Subscription Modification Elementary Procedure
--
-- **************************************************************
-- **************************************************************
--
-- RIC SUBSCRIPTION MODIFICATION REQUEST
--
-- **************************************************************
RICsubscriptionModificationRequest ::= SEQUENCE {
protocolIEs ProtocolIE-Container {{RICsubscriptionModificationRequest-IEs}},
...
}
RICsubscriptionModificationRequest-IEs E2AP-PROTOCOL-IES ::= {
{ ID id-RICrequestID CRITICALITY reject TYPE RICrequestID
PRESENCE mandatory}|
{ ID id-RANfunctionID CRITICALITY reject TYPE RANfunctionID
PRESENCE mandatory}|
{ ID id-RICeventTriggerDefinitionToBeModified CRITICALITY ignore TYPE RICeventTriggerDefinition
PRESENCE optional}|
{ ID id-RICactionsToBeRemovedForModification-List CRITICALITY ignore TYPE RICactions-ToBeRemovedForModification-List PRESENCE optional}|
{ ID id-RICactionsToBeModifiedForModification-List CRITICALITY ignore TYPE RICactions-ToBeModifiedForModification-List PRESENCE optional}|
{ ID id-RICactionsToBeAddedForModification-List CRITICALITY ignore TYPE RICactions-ToBeAddedForModification-List PRESENCE optional},
...
}
RICactions-ToBeRemovedForModification-List ::= SEQUENCE (SIZE(0..maxofRICactionID)) OF ProtocolIE-SingleContainer {{RICaction-ToBeRemovedForModification-ItemIEs} }
RICaction-ToBeRemovedForModification-ItemIEs E2AP-PROTOCOL-IES ::= {
{ ID id-RICaction-ToBeRemovedForModification-Item CRITICALITY ignore TYPE RICaction-ToBeRemovedForModification-Item PRESENCE mandatory },
...
}
RICaction-ToBeRemovedForModification-Item ::= SEQUENCE {
ricActionID RICactionID,
...
}
RICactions-ToBeModifiedForModification-List ::= SEQUENCE (SIZE(0..maxofRICactionID)) OF ProtocolIE-SingleContainer {{RICaction-ToBeModifiedForModification-ItemIEs} }
RICaction-ToBeModifiedForModification-ItemIEs E2AP-PROTOCOL-IES ::= {
{ ID id-RICaction-ToBeModifiedForModification-Item CRITICALITY ignore TYPE RICaction-ToBeModifiedForModification-Item PRESENCE mandatory },
...
}
RICaction-ToBeModifiedForModification-Item ::= SEQUENCE {
ricActionID RICactionID,
ricActionDefinition RICactionDefinition OPTIONAL,
ricActionExecutionOrder RICactionExecutionOrder OPTIONAL,
ricSubsequentAction RICsubsequentAction OPTIONAL,
...
}
RICactions-ToBeAddedForModification-List ::= SEQUENCE (SIZE(0..maxofRICactionID)) OF ProtocolIE-SingleContainer {{RICaction-ToBeAddedForModification-ItemIEs} }
RICaction-ToBeAddedForModification-ItemIEs E2AP-PROTOCOL-IES ::= {
{ ID id-RICaction-ToBeAddedForModification-Item CRITICALITY ignore TYPE RICaction-ToBeAddedForModification-Item PRESENCE mandatory },
...
}
RICaction-ToBeAddedForModification-Item ::= SEQUENCE {
ricActionID RICactionID,
ricActionType RICactionType,
ricActionDefinition RICactionDefinition,
ricActionExecutionOrder RICactionExecutionOrder,
ricSubsequentAction RICsubsequentAction OPTIONAL,
...
}
-- **************************************************************
--
-- RIC SUBSCRIPTION MODIFICATION RESPONSE
--
-- **************************************************************
RICsubscriptionModificationResponse ::= SEQUENCE {
protocolIEs ProtocolIE-Container {{RICsubscriptionModificationResponse-IEs}},
...
}
RICsubscriptionModificationResponse-IEs E2AP-PROTOCOL-IES ::= {
{ ID id-RICrequestID CRITICALITY reject TYPE RICrequestID
PRESENCE mandatory}|
{ ID id-RANfunctionID CRITICALITY reject TYPE RANfunctionID
PRESENCE mandatory}|
{ ID id-RICactionsRemovedForModification-List CRITICALITY ignore TYPE RICactions-RemovedForModification-List PRESENCE optional}|
{ ID id-RICactionsFailedToBeRemovedForModification-List CRITICALITY ignore TYPE RICactions-FailedToBeRemovedForModification-List PRESENCE optional}|
{ ID id-RICactionsModifiedForModification-List CRITICALITY ignore TYPE RICactions-ModifiedForModification-List PRESENCE optional}|
{ ID id-RICactionsFailedToBeModifiedForModification-List CRITICALITY ignore TYPE RICactions-FailedToBeModifiedForModification-List PRESENCE optional}|
{ ID id-RICactionsAddedForModification-List CRITICALITY ignore TYPE RICactions-AddedForModification-List PRESENCE optional}|
{ ID id-RICactionsFailedToBeAddedForModification-List CRITICALITY ignore TYPE RICactions-FailedToBeAddedForModification-List PRESENCE optional},
...
}
RICactions-RemovedForModification-List ::= SEQUENCE (SIZE(0..maxofRICactionID)) OF ProtocolIE-SingleContainer {{RICaction-RemovedForModification-ItemIEs} }
RICaction-RemovedForModification-ItemIEs E2AP-PROTOCOL-IES ::= {
{ ID id-RICaction-RemovedForModification-Item CRITICALITY ignore TYPE RICaction-RemovedForModification-Item PRESENCE mandatory },
...
}
RICaction-RemovedForModification-Item ::= SEQUENCE {
ricActionID RICactionID,
...
}
RICactions-FailedToBeRemovedForModification-List ::= SEQUENCE (SIZE(0..maxofRICactionID)) OF ProtocolIE-SingleContainer {{RICaction-FailedToBeRemovedForModification-ItemIEs} }
RICaction-FailedToBeRemovedForModification-ItemIEs E2AP-PROTOCOL-IES ::= {
{ ID id-RICaction-FailedToBeRemovedForModification-Item CRITICALITY ignore TYPE RICaction-FailedToBeRemovedForModification-Item PRESENCE mandatory },
...
}
RICaction-FailedToBeRemovedForModification-Item ::= SEQUENCE {
ricActionID RICactionID,
cause Cause,
...
}
RICactions-ModifiedForModification-List ::= SEQUENCE (SIZE(0..maxofRICactionID)) OF ProtocolIE-SingleContainer {{RICaction-ModifiedForModification-ItemIEs} }
RICaction-ModifiedForModification-ItemIEs E2AP-PROTOCOL-IES ::= {
{ ID id-RICaction-ModifiedForModification-Item CRITICALITY ignore TYPE RICaction-ModifiedForModification-Item PRESENCE mandatory },
...
}
RICaction-ModifiedForModification-Item ::= SEQUENCE {
ricActionID RICactionID,
...
}
RICactions-FailedToBeModifiedForModification-List ::= SEQUENCE (SIZE(0..maxofRICactionID)) OF ProtocolIE-SingleContainer {{RICaction-FailedToBeModifiedForModification-ItemIEs} }
RICaction-FailedToBeModifiedForModification-ItemIEs E2AP-PROTOCOL-IES ::= {
{ ID id-RICaction-FailedToBeModifiedForModification-Item CRITICALITY ignore TYPE RICaction-FailedToBeModifiedForModification-Item PRESENCE mandatory },
...
}
RICaction-FailedToBeModifiedForModification-Item ::= SEQUENCE {
ricActionID RICactionID,
cause Cause,
...
}
RICactions-AddedForModification-List ::= SEQUENCE (SIZE(0..maxofRICactionID)) OF ProtocolIE-SingleContainer {{RICaction-AddedForModification-ItemIEs} }
RICaction-AddedForModification-ItemIEs E2AP-PROTOCOL-IES ::= {
{ ID id-RICaction-AddedForModification-Item CRITICALITY ignore TYPE RICaction-AddedForModification-Item PRESENCE mandatory },
...
}
RICaction-AddedForModification-Item ::= SEQUENCE {
ricActionID RICactionID,
...
}
RICactions-FailedToBeAddedForModification-List ::= SEQUENCE (SIZE(0..maxofRICactionID)) OF ProtocolIE-SingleContainer {{RICaction-FailedToBeAddedForModification-ItemIEs} }
RICaction-FailedToBeAddedForModification-ItemIEs E2AP-PROTOCOL-IES ::= {
{ ID id-RICaction-FailedToBeAddedForModification-Item CRITICALITY ignore TYPE RICaction-FailedToBeAddedForModification-Item PRESENCE mandatory },
...
}
RICaction-FailedToBeAddedForModification-Item ::= SEQUENCE {
ricActionID RICactionID,
cause Cause,
...
}
-- **************************************************************
--
-- RIC SUBSCRIPTION MODIFICATION FAILURE
--
-- **************************************************************
RICsubscriptionModificationFailure ::= SEQUENCE {
protocolIEs ProtocolIE-Container {{RICsubscriptionModificationFailure-IEs}},
...
}
RICsubscriptionModificationFailure-IEs E2AP-PROTOCOL-IES ::= {
{ ID id-RICrequestID CRITICALITY reject TYPE RICrequestID PRESENCE
mandatory}|
{ ID id-RANfunctionID CRITICALITY reject TYPE RANfunctionID PRESENCE
mandatory}|
{ ID id-Cause CRITICALITY reject TYPE Cause PRESENCE mandatory}|
{ ID id-CriticalityDiagnostics CRITICALITY ignore TYPE CriticalityDiagnostics PRESENCE
optional},
...
}
-- **************************************************************
--
-- RIC Subscription Modification Required Elementary Procedure
--
-- **************************************************************
-- **************************************************************
--
-- RIC SUBSCRIPTION MODIFICATION REQUIRED
--
-- **************************************************************
RICsubscriptionModificationRequired ::= SEQUENCE {
protocolIEs ProtocolIE-Container {{RICsubscriptionModificationRequired-IEs}},
...
}
RICsubscriptionModificationRequired-IEs E2AP-PROTOCOL-IES ::= {
{ ID id-RICrequestID CRITICALITY reject TYPE RICrequestID
PRESENCE mandatory}|
{ ID id-RANfunctionID CRITICALITY reject TYPE RANfunctionID
PRESENCE mandatory}|
{ ID id-RICactionsRequiredToBeModified-List CRITICALITY ignore TYPE RICactions-RequiredToBeModified-List PRESENCE optional}|
{ ID id-RICactionsRequiredToBeRemoved-List CRITICALITY ignore TYPE RICactions-RequiredToBeRemoved-List PRESENCE optional},
...
}
RICactions-RequiredToBeModified-List ::= SEQUENCE (SIZE(0..maxofRICactionID)) OF ProtocolIE-SingleContainer {{RICaction-RequiredToBeModified-ItemIEs} }
RICaction-RequiredToBeModified-ItemIEs E2AP-PROTOCOL-IES ::= {
{ ID id-RICaction-RequiredToBeModified-Item CRITICALITY ignore TYPE RICaction-RequiredToBeModifiedItem PRESENCE mandatory },
...
}
RICaction-RequiredToBeModified-Item ::= SEQUENCE {
ricActionID RICactionID,
ricTimeToWait RICtimeToWait,
...
}
RICactions-RequiredToBeRemoved-List ::= SEQUENCE (SIZE(0..maxofRICactionID)) OF ProtocolIE-SingleContainer
{{RICaction-RequiredToBeRemoved-ItemIEs} }
RICaction-RequiredToBeRemoved-ItemIEs E2AP-PROTOCOL-IES ::= {
{ ID id-RICaction-RequiredToBeRemoved-Item CRITICALITY ignore TYPE RICaction-RequiredToBeRemovedItem PRESENCE mandatory },
...
}
RICaction-RequiredToBeRemoved-Item ::= SEQUENCE {
ricActionID RICactionID,
cause Cause,
...
}
-- **************************************************************
--
-- RIC SUBSCRIPTION MODIFICATION CONFIRM
--
-- **************************************************************
RICsubscriptionModificationConfirm ::= SEQUENCE {
protocolIEs ProtocolIE-Container {{RICsubscriptionModificationConfirm-IEs}},
...
}
RICsubscriptionModificationConfirm-IEs E2AP-PROTOCOL-IES ::= {
{ ID id-RICrequestID CRITICALITY reject TYPE RICrequestID
PRESENCE mandatory}|
{ ID id-RANfunctionID CRITICALITY reject TYPE RANfunctionID
PRESENCE mandatory}|
{ ID id-RICactionsConfirmedForModification-List CRITICALITY ignore TYPE RICactionsConfirmedForModification-List PRESENCE optional}|
{ ID id-RICactionsRefusedToBeModified-List CRITICALITY ignore TYPE RICactionsRefusedToBeModified-List PRESENCE optional}|
{ ID id-RICactionsConfirmedForRemoval-List CRITICALITY ignore TYPE RICactionsConfirmedForRemoval-List PRESENCE optional}|
{ ID id-RICactionsRefusedToBeRemoved-List CRITICALITY ignore TYPE RICactionsRefusedToBeRemoved-List PRESENCE optional},
...
}
RICactions-ConfirmedForModification-List ::= SEQUENCE (SIZE(0..maxofRICactionID)) OF ProtocolIE-SingleContainer {{RICaction-ConfirmedForModification-ItemIEs} }
RICaction-ConfirmedForModification-ItemIEs E2AP-PROTOCOL-IES ::= {
{ ID id-RICaction-ConfirmedForModification-Item CRITICALITY ignore TYPE RICaction-ConfirmedForModification-Item PRESENCE mandatory },
...
}
RICaction-ConfirmedForModification-Item ::= SEQUENCE {
ricActionID RICactionID,
...
}
RICactions-RefusedToBeModified-List ::= SEQUENCE (SIZE(0..maxofRICactionID)) OF ProtocolIE-SingleContainer
{{RICaction-RefusedToBeModified-ItemIEs} }
RICaction-RefusedToBeModified-ItemIEs E2AP-PROTOCOL-IES ::= {
{ ID id-RICaction-RefusedToBeModified-Item CRITICALITY ignore TYPE RICaction-RefusedToBeModified-Item PRESENCE mandatory },
...
}
RICaction-RefusedToBeModified-Item ::= SEQUENCE {
ricActionID RICactionID,
cause Cause,
...
}
RICactions-ConfirmedForRemoval-List ::= SEQUENCE (SIZE(0..maxofRICactionID)) OF ProtocolIE-SingleContainer
{{RICaction-ConfirmedForRemoval-ItemIEs} }
RICaction-ConfirmedForRemoval-ItemIEs E2AP-PROTOCOL-IES ::= {
{ ID id-RICaction-ConfirmedForRemoval-Item CRITICALITY ignore TYPE RICaction-ConfirmedForRemoval-Item PRESENCE mandatory },
...
}
RICaction-ConfirmedForRemoval-Item ::= SEQUENCE {
ricActionID RICactionID,
...
}
RICactions-RefusedToBeRemoved-List ::= SEQUENCE (SIZE(0..maxofRICactionID)) OF ProtocolIE-SingleContainer
{{RICaction-RefusedToBeRemoved-ItemIEs} }
RICaction-RefusedToBeRemoved-ItemIEs E2AP-PROTOCOL-IES ::= {
{ ID id-RICaction-RefusedToBeRemoved-Item CRITICALITY ignore TYPE RICaction-RefusedToBeRemoved-Item PRESENCE mandatory },
...
}
RICaction-RefusedToBeRemoved-Item ::= SEQUENCE {
ricActionID RICactionID,
cause Cause,
...
}
-- **************************************************************
--
-- RIC SUBSCRIPTION MODIFICATION REFUSE
--
-- **************************************************************
RICsubscriptionModificationRefuse ::= SEQUENCE {
protocolIEs ProtocolIE-Container {{RICsubscriptionModificationRefuse-IEs}},
...
}
RICsubscriptionModificationRefuse-IEs E2AP-PROTOCOL-IES ::= {
{ ID id-RICrequestID CRITICALITY reject TYPE RICrequestID PRESENCE
mandatory}|
{ ID id-RANfunctionID CRITICALITY reject TYPE RANfunctionID PRESENCE
mandatory}|
{ ID id-Cause CRITICALITY reject TYPE Cause PRESENCE mandatory}|
{ ID id-CriticalityDiagnostics CRITICALITY ignore TYPE CriticalityDiagnostics PRESENCE
optional},
...
}
-- **************************************************************
--
-- RIC Subscription State Control Elementary Procedure
--
-- **************************************************************
-- **************************************************************
--
-- RIC SUBSCRIPTION STATE CONTROL REQUEST
--
-- **************************************************************
RICsubscriptionStateControlRequest ::= SEQUENCE {
protocolIEs ProtocolIE-Container {{RICsubscriptionStateControlRequest-IEs}},
...
}
RICsubscriptionStateControlRequest-IEs E2AP-PROTOCOL-IES ::= {
{ ID id-RICrequestID CRITICALITY reject TYPE RICrequestID PRESENCE
mandatory }|
{ ID id-RANfunctionStateControl-List CRITICALITY reject TYPE RANfunctionStateControl-List PRESENCE
mandatory },
...
}
RANfunctionStateControl-List ::= SEQUENCE (SIZE(1..maxofRANfunctionID)) OF ProtocolIE-SingleContainer {
{RANfunctionStateControl-ItemIEs} }
RANfunctionStateControl-ItemIEs E2AP-PROTOCOL-IES ::= {
{ ID id-RANfunctionStateControl-Item CRITICALITY reject TYPE RANfunctionStateControl-Item
PRESENCE mandatory },
...
}
RANfunctionStateControl-Item ::= SEQUENCE {
ranFunctionID RANfunctionID,
ricSubscriptionToBeSuspended-list RICsubscriptionToBeSuspended-List OPTIONAL,
ricSubscriptionToBeResumed-list RICsubscriptionToBeResumed-List OPTIONAL,
...
}
RICsubscriptionToBeSuspended-List ::= SEQUENCE (SIZE(1..maxofRICrequestID)) OF ProtocolIE-SingleContainer
{ {RICsubscriptionList-ItemIEs} }
RICsubscriptionToBeResumed-List ::= SEQUENCE (SIZE(1..maxofRICrequestID)) OF ProtocolIE-SingleContainer {
{RICsubscriptionList-ItemIEs} }
RICsubscriptionList-ItemIEs E2AP-PROTOCOL-IES ::= {
{ ID id-RICsubscriptionList-Item CRITICALITY reject TYPE RICsubscriptionList-Item PRESENCE
mandatory },
...
}
RICsubscriptionList-Item ::= SEQUENCE {
ricRequestID RICrequestID,
ricAction-list RICaction-List OPTIONAL,
...
}
RICaction-List ::= SEQUENCE (SIZE(1..maxofRICactionID)) OF ProtocolIE-SingleContainer { {RICaction-ItemIEs} }
RICaction-ItemIEs E2AP-PROTOCOL-IES ::= {
{ ID id-RICactionList-Item CRITICALITY reject TYPE RICactionList-Item PRESENCE mandatory },
...
}
RICactionList-Item ::= SEQUENCE {
ricActionID RICactionID,
...
}
-- **************************************************************
--
-- RIC SUBSCRIPTION STATE CONTROL RESPONSE
--
-- **************************************************************
RICsubscriptionStateControlResponse ::= SEQUENCE {
protocolIEs ProtocolIE-Container {{RICsubscriptionStateControlResponse-IEs}},
...
}
RICsubscriptionStateControlResponse-IEs E2AP-PROTOCOL-IES ::= {
{ ID id-RICrequestID CRITICALITY reject TYPE RICrequestID PRESENCE
mandatory }|
{ ID id-RANfunctionStateConfirm-List CRITICALITY reject TYPE RANfunctionStateConfirm-List PRESENCE
mandatory },
...
}
RANfunctionStateConfirm-List ::= SEQUENCE (SIZE(1..maxofRANfunctionID)) OF ProtocolIE-SingleContainer {
{RANfunctionStateConfirm-ItemIEs} }
RANfunctionStateConfirm-ItemIEs E2AP-PROTOCOL-IES ::= {
{ ID id-RANfunctionStateConfirm-Item CRITICALITY reject TYPE RANfunctionStateConfirm-Item
PRESENCE mandatory },
...
}
RANfunctionStateConfirm-Item ::= SEQUENCE {
ranFunctionID RANfunctionID,
ricSubscriptionSuspended-list RICsubscriptionSuspended-List OPTIONAL,
ricSubscriptionResumed-list RICsubscriptionResumed-List OPTIONAL,
...
}
RICsubscriptionSuspended-List ::= SEQUENCE (SIZE(1..maxofRICrequestID)) OF ProtocolIE-SingleContainer {
{RICsubscriptionList-ItemIEs} }
RICsubscriptionResumed-List ::= SEQUENCE (SIZE(1..maxofRICrequestID)) OF ProtocolIE-SingleContainer {
{RICsubscriptionList-ItemIEs} }
-- **************************************************************
--
-- RIC SUBSCRIPTION STATE CONTROL FAILURE
--
-- **************************************************************
RICsubscriptionStateControlFailure ::= SEQUENCE {
protocolIEs ProtocolIE-Container {{RICsubscriptionStateControlFailure-IEs}},
...
}
RICsubscriptionStateControlFailure-IEs E2AP-PROTOCOL-IES ::= {
{ ID id-RICrequestID CRITICALITY reject TYPE RICrequestID
PRESENCE mandatory }|
{ ID id-Cause CRITICALITY reject TYPE Cause
PRESENCE mandatory }|
{ ID id-CriticalityDiagnostics CRITICALITY ignore TYPE CriticalityDiagnostics
PRESENCE optional },
...
}
-- **************************************************************
--
-- RIC Assistance Elementary Procedure
--
-- **************************************************************
-- **************************************************************
--
-- RIC ASSISTANCE REQUEST
--
-- **************************************************************
RICassistanceRequest ::= SEQUENCE {
protocolIEs ProtocolIE-Container {{RICassistanceRequest-IEs}},
...
}
RICassistanceRequest-IEs E2AP-PROTOCOL-IES ::= {
{ ID id-RICrequestID CRITICALITY reject TYPE RICrequestID PRESENCE
mandatory }|
{ ID id-RICassistanceHeader CRITICALITY reject TYPE RICassistanceHeader PRESENCE
mandatory }|
{ ID id-RICassistanceMessage CRITICALITY reject TYPE RICassistanceMessage PRESENCE
mandatory }|
{ ID id-RICassistanceUpdate CRITICALITY reject TYPE RICassistanceUpdate PRESENCE
optional }|
{ ID id-RICassistanceUpdateNumber CRITICALITY reject TYPE RICassistanceUpdateNumber PRESENCE
optional },
...
}
-- **************************************************************
--
-- RIC ASSISTANCE RESPONSE
--
-- **************************************************************
RICassistanceResponse ::= SEQUENCE {
protocolIEs ProtocolIE-Container {{RICassistanceResponse-IEs}},
...
}
RICassistanceResponse-IEs E2AP-PROTOCOL-IES ::= {
{ ID id-RICrequestID CRITICALITY reject TYPE RICrequestID PRESENCE
mandatory }|
{ ID id-RICassistanceHeader CRITICALITY reject TYPE RICassistanceHeader PRESENCE
mandatory }|
{ ID id-RICassistanceOutcome CRITICALITY reject TYPE RICassistanceOutcome PRESENCE
mandatory },
...
}
-- **************************************************************
--
-- RIC ASSISTANCE FAILURE
--
-- **************************************************************
RICassistanceFailure ::= SEQUENCE {
protocolIEs ProtocolIE-Container {{RICassistanceFailure-IEs}},
...
}
RICassistanceFailure-IEs E2AP-PROTOCOL-IES ::= {
{ ID id-RICrequestID CRITICALITY reject TYPE RICrequestID PRESENCE
mandatory }|
{ ID id-Cause CRITICALITY ignore TYPE Cause PRESENCE
mandatory }|
{ ID id-CriticalityDiagnostics CRITICALITY ignore TYPE CriticalityDiagnostics PRESENCE
optional },
...
}
-- **************************************************************
--
-- RIC Assistance Indication Elementary Procedure
--
-- **************************************************************
-- **************************************************************
--
-- RIC ASSISTANCE INDICATION
--
-- **************************************************************
RICassistanceIndication ::= SEQUENCE {
protocolIEs ProtocolIE-Container {{RICassistanceIndication-IEs}},
...
}
RICassistanceIndication-IEs E2AP-PROTOCOL-IES ::= {
{ ID id-RICrequestID CRITICALITY reject TYPE RICrequestID PRESENCE
mandatory }|
{ ID id-RICassistanceSN CRITICALITY reject TYPE RICassistanceSN PRESENCE
mandatory }|
{ ID id-RICassistanceHeader CRITICALITY reject TYPE RICassistanceHeader PRESENCE
mandatory }|
{ ID id-RICassistanceOutcome CRITICALITY reject TYPE RICassistanceOutcome PRESENCE
mandatory },
...
}
-- **************************************************************
--
-- RIC Assistance Halt Elementary Procedure
--
-- **************************************************************
-- **************************************************************
--
-- RIC ASSISTANCE HALT
--
-- **************************************************************
RICassistanceHalt ::= SEQUENCE {
protocolIEs ProtocolIE-Container {{RICassistanceHalt-IEs}},
...
}
RICassistanceHalt-IEs E2AP-PROTOCOL-IES ::= {
{ ID id-RICrequestID CRITICALITY reject TYPE RICrequestID PRESENCE
mandatory },
...
}
-- **************************************************************
--
-- RIC Indication Elementary Procedure
--
-- **************************************************************
-- **************************************************************
--
-- RIC INDICATION
--
-- **************************************************************
RICindication ::= SEQUENCE {
protocolIEs ProtocolIE-Container {{RICindication-IEs}},
...
}
RICindication-IEs E2AP-PROTOCOL-IES ::= {
{ ID id-RICrequestID CRITICALITY reject TYPE RICrequestID PRESENCE
mandatory }|
{ ID id-RANfunctionID CRITICALITY reject TYPE RANfunctionID PRESENCE
mandatory }|
{ ID id-RICactionID CRITICALITY reject TYPE RICactionID PRESENCE
mandatory }|
{ ID id-RICindicationSN CRITICALITY reject TYPE RICindicationSN PRESENCE
optional }|
{ ID id-RICindicationType CRITICALITY reject TYPE RICindicationType PRESENCE
mandatory }|
{ ID id-RICindicationHeader CRITICALITY reject TYPE RICindicationHeader PRESENCE
mandatory }|
{ ID id-RICindicationMessage CRITICALITY reject TYPE RICindicationMessage PRESENCE
mandatory }|
{ ID id-RICcallProcessID CRITICALITY reject TYPE RICcallProcessID PRESENCE
optional },
...
}
-- **************************************************************
--
-- RIC Control Elementary Procedure
--
-- **************************************************************
-- **************************************************************
--
-- RIC CONTROL REQUEST
--
-- **************************************************************
RICcontrolRequest ::= SEQUENCE {
protocolIEs ProtocolIE-Container {{RICcontrolRequest-IEs}},
...
}
RICcontrolRequest-IEs E2AP-PROTOCOL-IES ::= {
{ ID id-RICrequestID CRITICALITY reject TYPE RICrequestID PRESENCE
mandatory }|
{ ID id-RANfunctionID CRITICALITY reject TYPE RANfunctionID PRESENCE
mandatory }|
{ ID id-RICcallProcessID CRITICALITY reject TYPE RICcallProcessID PRESENCE
optional }|
{ ID id-RICcontrolHeader CRITICALITY reject TYPE RICcontrolHeader PRESENCE
mandatory }|
{ ID id-RICcontrolMessage CRITICALITY reject TYPE RICcontrolMessage PRESENCE
mandatory }|
{ ID id-RICcontrolAckRequest CRITICALITY reject TYPE RICcontrolAckRequest PRESENCE
optional },
...
}
-- **************************************************************
--
-- RIC CONTROL ACKNOWLEDGE
--
-- **************************************************************
RICcontrolAcknowledge ::= SEQUENCE {
protocolIEs ProtocolIE-Container {{RICcontrolAcknowledge-IEs}},
...
}
RICcontrolAcknowledge-IEs E2AP-PROTOCOL-IES ::= {
{ ID id-RICrequestID CRITICALITY reject TYPE RICrequestID PRESENCE
mandatory }|
{ ID id-RANfunctionID CRITICALITY reject TYPE RANfunctionID PRESENCE
mandatory }|
{ ID id-RICcallProcessID CRITICALITY reject TYPE RICcallProcessID PRESENCE
optional }|
{ ID id-RICcontrolOutcome CRITICALITY reject TYPE RICcontrolOutcome PRESENCE
optional },
...
}
-- **************************************************************
--
-- RIC CONTROL FAILURE
--
-- **************************************************************
RICcontrolFailure ::= SEQUENCE {
protocolIEs ProtocolIE-Container {{RICcontrolFailure-IEs}},
...
}
RICcontrolFailure-IEs E2AP-PROTOCOL-IES ::= {
{ ID id-RICrequestID CRITICALITY reject TYPE RICrequestID PRESENCE
mandatory }|
{ ID id-RANfunctionID CRITICALITY reject TYPE RANfunctionID PRESENCE
mandatory }|
{ ID id-RICcallProcessID CRITICALITY reject TYPE RICcallProcessID PRESENCE
optional }|
{ ID id-Cause CRITICALITY ignore TYPE Cause PRESENCE
mandatory }|
{ ID id-RICcontrolOutcome CRITICALITY reject TYPE RICcontrolOutcome PRESENCE
optional },
...,
{ ID id-CriticalityDiagnostics CRITICALITY ignore TYPE CriticalityDiagnostics PRESENCE
optional }
}
-- **************************************************************
--
-- RIC QUERY Elementary Procedure
--
-- **************************************************************
-- **************************************************************
--
-- RIC QUERY REQUEST
--
-- **************************************************************
RICqueryRequest ::= SEQUENCE {
protocolIEs ProtocolIE-Container {{RICqueryRequest-IEs}},
...
}
RICqueryRequest-IEs E2AP-PROTOCOL-IES ::= {
{ ID id-RICrequestID CRITICALITY reject TYPE RICrequestID PRESENCE
mandatory }|
{ ID id-RANfunctionID CRITICALITY reject TYPE RANfunctionID PRESENCE
mandatory }|
{ ID id-RICqueryHeader CRITICALITY reject TYPE RICqueryHeader PRESENCE
mandatory }|
{ ID id-RICqueryDefinition CRITICALITY reject TYPE RICqueryDefinition PRESENCE
mandatory },
...
}
-- **************************************************************
--
-- RIC QUERY RESPONSE
--
-- **************************************************************
RICqueryResponse ::= SEQUENCE {
protocolIEs ProtocolIE-Container {{RICqueryResponse-IEs}},
...
}
RICqueryResponse-IEs E2AP-PROTOCOL-IES ::= {
{ ID id-RICrequestID CRITICALITY reject TYPE RICrequestID PRESENCE
mandatory }|
{ ID id-RANfunctionID CRITICALITY reject TYPE RANfunctionID PRESENCE
mandatory }|
{ ID id-RICqueryOutcome CRITICALITY reject TYPE RICqueryOutcome PRESENCE
mandatory },
...
}
-- **************************************************************
--
-- RIC QUERY FAILURE
--
-- **************************************************************
RICqueryFailure ::= SEQUENCE {
protocolIEs ProtocolIE-Container {{RICqueryFailure-IEs}},
...
}
RICqueryFailure-IEs E2AP-PROTOCOL-IES ::= {
{ ID id-RICrequestID CRITICALITY reject TYPE RICrequestID PRESENCE
mandatory }|
{ ID id-RANfunctionID CRITICALITY reject TYPE RANfunctionID PRESENCE
mandatory }|
{ ID id-Cause CRITICALITY ignore TYPE Cause PRESENCE
mandatory }|
{ ID id-CriticalityDiagnostics CRITICALITY ignore TYPE CriticalityDiagnostics PRESENCE
optional },
...
}
-- **************************************************************
--
-- RIC Service Load Status Elementary Procedure
--
-- **************************************************************
-- **************************************************************
--
-- RIC SERVICE LOAD STATUS REQUEST
--
-- **************************************************************
RICserviceLoadStatusRequest ::= SEQUENCE {
protocolIEs ProtocolIE-Container {{RICserviceLoadStatusRequest-IEs}},
...
}
RICserviceLoadStatusRequest-IEs E2AP-PROTOCOL-IES ::= {
{ ID id-RICloadMeasurementID CRITICALITY reject TYPE LoadMeasurementID PRESENCE
mandatory }|
{ ID id-E2nodeLoadMeasurementID CRITICALITY ignore TYPE LoadMeasurementID PRESENCE
conditional}|
{ ID id-RegistrationRequest CRITICALITY ignore TYPE RegistrationRequest PRESENCE
mandatory }|
{ ID id-RANfunctionLoadRequest-List CRITICALITY reject TYPE RANfunctionLoadRequest-List PRESENCE
conditional }|
{ ID id-ReportingPeriodicity CRITICALITY ignore TYPE ReportingPeriodicity PRESENCE
optional },
...
}
RANfunctionLoadRequest-List ::= SEQUENCE (SIZE(1..maxofRANfunctionID)) OF ProtocolIE-SingleContainer {
{RANfunctionLoadRequest-ItemIEs} }
RANfunctionLoadRequest-ItemIEs E2AP-PROTOCOL-IES ::= {
{ ID id-RANfunctionLoadRequest-Item CRITICALITY reject TYPE RANfunctionLoadRequest-Item PRESENCE
mandatory },
...
}
RANfunctionLoadRequest-Item ::= SEQUENCE {
ranFunctionID RANfunctionID,
ranFunctionLoadRequest RICloadRequest OPTIONAL,
ricServiceLoadRequest RICserviceLoadRequest OPTIONAL,
ricSubscriptionLoadRequest-list RICsubscriptionLoadRequest-List OPTIONAL,
...
}
RICsubscriptionLoadRequest-List ::= SEQUENCE (SIZE(1..maxofRICrequestID)) OF ProtocolIE-SingleContainer {
{RICsubscriptionLoadRequest-ItemIEs} }
RICsubscriptionLoadRequest-ItemIEs E2AP-PROTOCOL-IES ::= {
        { ID id-RICsubscriptionLoadRequest-Item CRITICALITY reject TYPE RICsubscriptionLoadRequest-ItemIE
PRESENCE mandatory },
...
}
RICsubscriptionLoadRequest-ItemIE ::= SEQUENCE {
ricRequestID RICrequestID,
ricSubscriptionLoadRequest RICloadRequest OPTIONAL,
ricActionLoadRequest-list RICactionLoadRequest-List OPTIONAL,
...
}
RICactionLoadRequest-List ::= SEQUENCE (SIZE(1..maxofRICactionID)) OF ProtocolIE-SingleContainer {
{RICactionLoadRequest-ItemIEs} }
RICactionLoadRequest-ItemIEs E2AP-PROTOCOL-IES ::= {
{ ID id-RICactionLoadRequest-Item CRITICALITY reject TYPE RICactionLoadRequest-Item
PRESENCE mandatory },
...
}
RICactionLoadRequest-Item ::= SEQUENCE {
ricActionID RICactionID,
ricActionLoadRequest RICloadRequest,
...
}
-- **************************************************************
--
-- RIC SERVICE LOAD STATUS RESPONSE
--
-- **************************************************************
RICserviceLoadStatusResponse ::= SEQUENCE {
protocolIEs ProtocolIE-Container {{RICserviceLoadStatusResponse-IEs}},
...
}
RICserviceLoadStatusResponse-IEs E2AP-PROTOCOL-IES ::= {
{ ID id-RICloadMeasurementID CRITICALITY reject TYPE LoadMeasurementID PRESENCE
mandatory }|
{ ID id-E2nodeLoadMeasurementID CRITICALITY ignore TYPE LoadMeasurementID PRESENCE
mandatory }|
{ ID id-RANfunctionLoadConfirm-List CRITICALITY reject TYPE RANfunctionLoadConfirm-List PRESENCE
conditional },
...
}
RANfunctionLoadConfirm-List ::= SEQUENCE (SIZE(1..maxofRANfunctionID)) OF ProtocolIE-SingleContainer {
{RANfunctionLoadConfirm-ItemIEs} }
RANfunctionLoadConfirm-ItemIEs E2AP-PROTOCOL-IES ::= {
{ ID id-RANfunctionLoadConfirm-Item CRITICALITY reject TYPE RANfunctionLoadConfirm-Item PRESENCE
mandatory },
...
}
RANfunctionLoadConfirm-Item ::= SEQUENCE {
ranFunctionID RANfunctionID,
ranFunctionLoadConfirm RICloadConfirm OPTIONAL,
ricServiceLoadConfirm RICserviceLoadConfirm OPTIONAL,
ricSubscriptionLoadConfirm-list RICsubscriptionLoadConfirm-List OPTIONAL,
...
}
RICsubscriptionLoadConfirm-List ::= SEQUENCE (SIZE(1..maxofRICrequestID)) OF ProtocolIE-SingleContainer {
{RICsubscriptionLoadConfirm-ItemIEs} }
RICsubscriptionLoadConfirm-ItemIEs E2AP-PROTOCOL-IES ::= {
{ ID id-RICsubscriptionLoadConfirm-Item CRITICALITY reject TYPE RICsubscriptionLoadConfirm-ItemIE
PRESENCE mandatory },
...
}
RICsubscriptionLoadConfirm-ItemIE ::= SEQUENCE {
ricRequestID RICrequestID,
ricSubscriptionLoadConfirm RICloadConfirm OPTIONAL,
ricActionLoadConfirm-list RICactionLoadConfirm-List OPTIONAL,
...
}
RICactionLoadConfirm-List ::= SEQUENCE (SIZE(1..maxofRICactionID)) OF ProtocolIE-SingleContainer {
{RICactionLoadConfirm-ItemIEs} }
RICactionLoadConfirm-ItemIEs E2AP-PROTOCOL-IES ::= {
{ ID id-RICactionLoadConfirm-Item CRITICALITY reject TYPE RICactionLoadConfirm-Item
PRESENCE mandatory },
...
}
RICactionLoadConfirm-Item ::= SEQUENCE {
ricActionID RICactionID,
ricActionLoadConfirm RICloadConfirm,
...
}
-- **************************************************************
--
-- RIC SERVICE LOAD STATUS FAILURE
--
-- **************************************************************
RICserviceLoadStatusFailure ::= SEQUENCE {
protocolIEs ProtocolIE-Container {{RICserviceLoadStatusFailure-IEs}},
...
}
RICserviceLoadStatusFailure-IEs E2AP-PROTOCOL-IES ::= {
{ ID id-RICloadMeasurementID CRITICALITY reject TYPE LoadMeasurementID PRESENCE
mandatory }|
{ ID id-E2nodeLoadMeasurementID CRITICALITY ignore TYPE LoadMeasurementID PRESENCE
mandatory }|
{ ID id-Cause CRITICALITY ignore TYPE Cause PRESENCE
mandatory }|
{ ID id-CriticalityDiagnostics CRITICALITY ignore TYPE CriticalityDiagnostics PRESENCE
optional },
...
}
-- **************************************************************
--
-- RIC Service Load Update Elementary Procedure
--
-- **************************************************************
-- **************************************************************
--
-- RIC SERVICE LOAD UPDATE
--
-- **************************************************************
RICserviceLoadUpdate ::= SEQUENCE {
protocolIEs ProtocolIE-Container {{RICserviceLoadUpdate-IEs}},
...
}
RICserviceLoadUpdate-IEs E2AP-PROTOCOL-IES ::= {
{ ID id-RICloadMeasurementID CRITICALITY reject TYPE LoadMeasurementID PRESENCE
mandatory }|
{ ID id-E2nodeLoadMeasurementID CRITICALITY ignore TYPE LoadMeasurementID PRESENCE
mandatory }|
{ ID id-RANfunctionLoad-List CRITICALITY reject TYPE RANfunctionLoad-List PRESENCE
mandatory },
...
}
RANfunctionLoad-List ::= SEQUENCE (SIZE(1..maxofRANfunctionID)) OF ProtocolIE-SingleContainer {
{RANfunctionLoad-ItemIEs} }
RANfunctionLoad-ItemIEs E2AP-PROTOCOL-IES ::= {
{ ID id-RANfunctionLoad-Item CRITICALITY reject TYPE RANfunctionLoad-Item PRESENCE
mandatory },
...
}
RANfunctionLoad-Item ::= SEQUENCE {
ranFunctionID RANfunctionID,
ranFunctionLoadInformation RICloadInformation OPTIONAL,
ricServiceLoadInformation RICserviceLoadInformation OPTIONAL,
ricSubscriptionLoad-list RICsubscriptionLoad-List OPTIONAL,
...
}
RICsubscriptionLoad-List ::= SEQUENCE (SIZE(1..maxofRICrequestID)) OF ProtocolIE-SingleContainer {
{RICsubscriptionLoad-ItemIEs} }
RICsubscriptionLoad-ItemIEs E2AP-PROTOCOL-IES ::= {
{ ID id-RICsubscriptionLoad-Item CRITICALITY reject TYPE RICsubscriptionLoad-ItemIE PRESENCE
mandatory },
...
}
RICsubscriptionLoad-ItemIE ::= SEQUENCE {
ricRequestID RICrequestID,
ricSubscriptionLoadInformation RICloadInformation OPTIONAL,
ricActionLoad-list RICactionLoad-List OPTIONAL,
...
}
RICactionLoad-List ::= SEQUENCE (SIZE(1..maxofRICactionID)) OF ProtocolIE-SingleContainer {
{RICactionLoad-ItemIEs} }
RICactionLoad-ItemIEs E2AP-PROTOCOL-IES ::= {
{ ID id-RICactionLoad-Item CRITICALITY reject TYPE RICactionLoad-Item PRESENCE
mandatory },
...
}
RICactionLoad-Item ::= SEQUENCE {
ricActionID RICactionID,
ricActionLoadInformation RICloadInformation,
...
}
-- **************************************************************
--
-- MESSAGES FOR GLOBAL PROCEDURES
--
-- **************************************************************
-- **************************************************************
--
-- Error Indication Elementary Procedure
--
-- **************************************************************
-- **************************************************************
--
-- ERROR INDICATION
--
-- **************************************************************
ErrorIndication ::= SEQUENCE {
protocolIEs ProtocolIE-Container {{ErrorIndication-IEs}},
...
}
ErrorIndication-IEs E2AP-PROTOCOL-IES ::= {
        { ID id-TransactionID CRITICALITY reject TYPE TransactionID PRESENCE
optional }|
{ ID id-RICrequestID CRITICALITY reject TYPE RICrequestID PRESENCE
optional }|
{ ID id-RANfunctionID CRITICALITY reject TYPE RANfunctionID PRESENCE
optional }|
{ ID id-Cause CRITICALITY ignore TYPE Cause PRESENCE
optional }|
{ ID id-CriticalityDiagnostics CRITICALITY ignore TYPE CriticalityDiagnostics PRESENCE
optional },
...
}
-- **************************************************************
--
-- E2 Setup Elementary Procedure
--
-- **************************************************************
-- **************************************************************
--
-- E2 SETUP REQUEST
--
-- **************************************************************
E2setupRequest ::= SEQUENCE {
protocolIEs ProtocolIE-Container { {E2setupRequestIEs} },
...
}
E2setupRequestIEs E2AP-PROTOCOL-IES ::= {
{ ID id-TransactionID CRITICALITY reject TYPE TransactionID
PRESENCE mandatory }|
{ ID id-GlobalE2node-ID CRITICALITY reject TYPE GlobalE2node-ID PRESENCE
mandatory }|
{ ID id-RANfunctionsAdded CRITICALITY reject TYPE RANfunctions-List PRESENCE
mandatory }|
{ ID id-E2nodeComponentConfigAddition CRITICALITY reject TYPE E2nodeComponentConfigAddition-List
PRESENCE mandatory },
...
}
-- **************************************************************
--
-- E2 SETUP RESPONSE
--
-- **************************************************************
E2setupResponse ::= SEQUENCE {
protocolIEs ProtocolIE-Container { {E2setupResponseIEs} },
...
}
E2setupResponseIEs E2AP-PROTOCOL-IES ::= {
{ ID id-TransactionID CRITICALITY reject TYPE TransactionID
PRESENCE mandatory }|
{ ID id-GlobalRIC-ID CRITICALITY reject TYPE GlobalRIC-ID
PRESENCE mandatory }|
{ ID id-RANfunctionsAccepted CRITICALITY reject TYPE RANfunctionsID-List
PRESENCE optional }|
{ ID id-RANfunctionsRejected CRITICALITY reject TYPE RANfunctionsIDcause-List
PRESENCE optional }|
{ ID id-E2nodeComponentConfigAdditionAck CRITICALITY reject TYPE E2nodeComponentConfigAdditionAck-List PRESENCE mandatory },
...
}
-- **************************************************************
--
-- E2 SETUP FAILURE
--
-- **************************************************************
E2setupFailure ::= SEQUENCE {
protocolIEs ProtocolIE-Container { {E2setupFailureIEs} },
...
}
E2setupFailureIEs E2AP-PROTOCOL-IES ::= {
{ ID id-TransactionID CRITICALITY reject TYPE TransactionID PRESENCE
mandatory }|
{ ID id-Cause CRITICALITY ignore TYPE Cause PRESENCE
mandatory }|
{ ID id-TimeToWait CRITICALITY ignore TYPE TimeToWait PRESENCE
optional }|
{ ID id-CriticalityDiagnostics CRITICALITY ignore TYPE CriticalityDiagnostics PRESENCE
optional }|
{ ID id-TNLinformation CRITICALITY ignore TYPE TNLinformation PRESENCE
optional },
...
}
-- **************************************************************
--
-- E2 Connection Update Elementary Procedure
--
-- **************************************************************
-- **************************************************************
--
-- E2 CONNECTION UPDATE
--
-- **************************************************************
E2connectionUpdate ::= SEQUENCE {
protocolIEs ProtocolIE-Container {{E2connectionUpdate-IEs}},
...
}
E2connectionUpdate-IEs E2AP-PROTOCOL-IES ::= {
{ ID id-TransactionID CRITICALITY reject TYPE TransactionID PRESENCE
mandatory }|
{ ID id-E2connectionUpdateAdd CRITICALITY reject TYPE E2connectionUpdate-List PRESENCE
optional }|
{ ID id-E2connectionUpdateRemove CRITICALITY reject TYPE E2connectionUpdateRemove-List PRESENCE
optional }|
{ ID id-E2connectionUpdateModify CRITICALITY reject TYPE E2connectionUpdate-List PRESENCE
optional },
...
}
E2connectionUpdate-List ::= SEQUENCE (SIZE(1..maxofTNLA)) OF ProtocolIE-SingleContainer {
{E2connectionUpdate-ItemIEs} }
E2connectionUpdate-ItemIEs E2AP-PROTOCOL-IES ::= {
{ ID id-E2connectionUpdate-Item CRITICALITY ignore TYPE E2connectionUpdate-Item PRESENCE
mandatory },
...
}
E2connectionUpdate-Item ::= SEQUENCE {
tnlInformation TNLinformation,
tnlUsage TNLusage,
...
}
E2connectionUpdateRemove-List ::= SEQUENCE (SIZE(1..maxofTNLA)) OF ProtocolIE-SingleContainer {
{E2connectionUpdateRemove-ItemIEs} }
E2connectionUpdateRemove-ItemIEs E2AP-PROTOCOL-IES ::= {
{ ID id-E2connectionUpdateRemove-Item CRITICALITY ignore TYPE E2connectionUpdateRemove-Item
PRESENCE mandatory },
...
}
E2connectionUpdateRemove-Item ::= SEQUENCE {
tnlInformation TNLinformation,
...
}
-- **************************************************************
--
-- E2 CONNECTION UPDATE ACKNOWLEDGE
--
-- **************************************************************
E2connectionUpdateAcknowledge ::= SEQUENCE {
protocolIEs ProtocolIE-Container {{E2connectionUpdateAck-IEs}},
...
}
E2connectionUpdateAck-IEs E2AP-PROTOCOL-IES ::= {
{ ID id-TransactionID CRITICALITY reject TYPE TransactionID PRESENCE
mandatory }|
{ ID id-E2connectionSetup CRITICALITY reject TYPE E2connectionUpdate-List PRESENCE
optional }|
{ ID id-E2connectionSetupFailed CRITICALITY reject TYPE E2connectionSetupFailed-List PRESENCE
optional },
...
}
E2connectionSetupFailed-List ::= SEQUENCE (SIZE(1..maxofTNLA)) OF ProtocolIE-SingleContainer {
{E2connectionSetupFailed-ItemIEs} }
E2connectionSetupFailed-ItemIEs E2AP-PROTOCOL-IES ::= {
{ ID id-E2connectionSetupFailed-Item CRITICALITY ignore TYPE E2connectionSetupFailed-Item
PRESENCE mandatory },
...
}
E2connectionSetupFailed-Item ::= SEQUENCE {
tnlInformation TNLinformation,
cause Cause,
...
}
-- **************************************************************
--
-- E2 CONNECTION UPDATE FAILURE
--
-- **************************************************************
E2connectionUpdateFailure ::= SEQUENCE {
protocolIEs ProtocolIE-Container {{E2connectionUpdateFailure-IEs}},
...
}
E2connectionUpdateFailure-IEs E2AP-PROTOCOL-IES ::= {
{ ID id-TransactionID CRITICALITY reject TYPE TransactionID
PRESENCE mandatory }|
{ ID id-Cause CRITICALITY reject TYPE Cause
PRESENCE optional }|
{ ID id-TimeToWait CRITICALITY ignore TYPE TimeToWait
PRESENCE optional }|
{ ID id-CriticalityDiagnostics CRITICALITY ignore TYPE CriticalityDiagnostics
PRESENCE optional },
...
}
-- **************************************************************
--
-- E2 Node Configuration Update Elementary Procedure
--
-- **************************************************************
-- **************************************************************
--
-- E2 NODE CONFIGURATION UPDATE
--
-- **************************************************************
E2nodeConfigurationUpdate ::= SEQUENCE {
protocolIEs ProtocolIE-Container {{E2nodeConfigurationUpdate-IEs}},
...
}
E2nodeConfigurationUpdate-IEs E2AP-PROTOCOL-IES ::= {
{ ID id-TransactionID CRITICALITY reject TYPE TransactionID
PRESENCE mandatory }|
{ ID id-GlobalE2node-ID CRITICALITY reject TYPE GlobalE2node-ID
PRESENCE optional }|
{ ID id-E2nodeComponentConfigAddition CRITICALITY reject TYPE E2nodeComponentConfigAddition-List
PRESENCE optional }|
{ ID id-E2nodeComponentConfigUpdate CRITICALITY reject TYPE E2nodeComponentConfigUpdate-List
PRESENCE optional }|
{ ID id-E2nodeComponentConfigRemoval CRITICALITY reject TYPE E2nodeComponentConfigRemoval-List
PRESENCE optional }|
{ ID id-E2nodeTNLassociationRemoval CRITICALITY reject TYPE E2nodeTNLassociationRemoval-List
PRESENCE optional },
...
}
E2nodeComponentConfigAddition-List ::= SEQUENCE (SIZE(1..maxofE2nodeComponents)) OF ProtocolIE-SingleContainer { {E2nodeComponentConfigAddition-ItemIEs} }
E2nodeComponentConfigAddition-ItemIEs E2AP-PROTOCOL-IES ::= {
{ ID id-E2nodeComponentConfigAddition-Item CRITICALITY reject TYPE E2nodeComponentConfigAddition-Item PRESENCE mandatory },
...
}
E2nodeComponentConfigAddition-Item ::= SEQUENCE {
e2nodeComponentInterfaceType E2nodeComponentInterfaceType,
e2nodeComponentID E2nodeComponentID,
e2nodeComponentConfiguration E2nodeComponentConfiguration,
...
}
E2nodeComponentConfigUpdate-List ::= SEQUENCE (SIZE(1..maxofE2nodeComponents)) OF ProtocolIE-SingleContainer { {E2nodeComponentConfigUpdate-ItemIEs} }
E2nodeComponentConfigUpdate-ItemIEs E2AP-PROTOCOL-IES ::= {
{ ID id-E2nodeComponentConfigUpdate-Item CRITICALITY reject TYPE E2nodeComponentConfigUpdate-Item
PRESENCE mandatory },
...
}
E2nodeComponentConfigUpdate-Item ::= SEQUENCE {
e2nodeComponentInterfaceType E2nodeComponentInterfaceType,
e2nodeComponentID E2nodeComponentID,
e2nodeComponentConfiguration E2nodeComponentConfiguration,
...
}
E2nodeComponentConfigRemoval-List ::= SEQUENCE (SIZE(1..maxofE2nodeComponents)) OF ProtocolIE-SingleContainer { {E2nodeComponentConfigRemoval-ItemIEs} }
E2nodeComponentConfigRemoval-ItemIEs E2AP-PROTOCOL-IES ::= {
{ ID id-E2nodeComponentConfigRemoval-Item CRITICALITY reject TYPE E2nodeComponentConfigRemoval-Item
PRESENCE mandatory },
...
}
E2nodeComponentConfigRemoval-Item ::= SEQUENCE {
e2nodeComponentInterfaceType E2nodeComponentInterfaceType,
e2nodeComponentID E2nodeComponentID,
...
}
E2nodeTNLassociationRemoval-List ::= SEQUENCE (SIZE(1..maxofTNLA)) OF ProtocolIE-SingleContainer {
{E2nodeTNLassociationRemoval-ItemIEs} }
E2nodeTNLassociationRemoval-ItemIEs E2AP-PROTOCOL-IES ::= {
{ ID id-E2nodeTNLassociationRemoval-Item CRITICALITY reject TYPE E2nodeTNLassociationRemoval-Item
PRESENCE mandatory },
...
}
E2nodeTNLassociationRemoval-Item ::= SEQUENCE {
tnlInformation TNLinformation,
tnlInformationRIC TNLinformation,
...
}
-- **************************************************************
--
-- E2 NODE CONFIGURATION UPDATE ACKNOWLEDGE
--
-- **************************************************************
E2nodeConfigurationUpdateAcknowledge ::= SEQUENCE {
protocolIEs ProtocolIE-Container {{E2nodeConfigurationUpdateAcknowledge-IEs}},
...
}
E2nodeConfigurationUpdateAcknowledge-IEs E2AP-PROTOCOL-IES ::= {
{ ID id-TransactionID CRITICALITY reject TYPE TransactionID
PRESENCE mandatory }|
{ ID id-E2nodeComponentConfigAdditionAck CRITICALITY reject TYPE
E2nodeComponentConfigAdditionAck-List PRESENCE optional }|
{ ID id-E2nodeComponentConfigUpdateAck CRITICALITY reject TYPE
E2nodeComponentConfigUpdateAck-List PRESENCE optional }|
{ ID id-E2nodeComponentConfigRemovalAck CRITICALITY reject TYPE
E2nodeComponentConfigRemovalAck-List PRESENCE optional },
...
}
E2nodeComponentConfigAdditionAck-List ::= SEQUENCE (SIZE(1..maxofE2nodeComponents)) OF ProtocolIE-SingleContainer { {E2nodeComponentConfigAdditionAck-ItemIEs} }
E2nodeComponentConfigAdditionAck-ItemIEs E2AP-PROTOCOL-IES ::= {
{ ID id-E2nodeComponentConfigAdditionAck-Item CRITICALITY reject TYPE
E2nodeComponentConfigAdditionAck-Item PRESENCE mandatory },
...
}
E2nodeComponentConfigAdditionAck-Item ::= SEQUENCE {
e2nodeComponentInterfaceType E2nodeComponentInterfaceType,
e2nodeComponentID E2nodeComponentID,
e2nodeComponentConfigurationAck E2nodeComponentConfigurationAck,
...
}
E2nodeComponentConfigUpdateAck-List ::= SEQUENCE (SIZE(1..maxofE2nodeComponents)) OF ProtocolIE-SingleContainer { {E2nodeComponentConfigUpdateAck-ItemIEs} }
E2nodeComponentConfigUpdateAck-ItemIEs E2AP-PROTOCOL-IES ::= {
{ ID id-E2nodeComponentConfigUpdateAck-Item CRITICALITY reject TYPE
E2nodeComponentConfigUpdateAck-Item PRESENCE mandatory },
...
}
E2nodeComponentConfigUpdateAck-Item ::= SEQUENCE {
e2nodeComponentInterfaceType E2nodeComponentInterfaceType,
e2nodeComponentID E2nodeComponentID,
e2nodeComponentConfigurationAck E2nodeComponentConfigurationAck,
...
}
E2nodeComponentConfigRemovalAck-List ::= SEQUENCE (SIZE(1..maxofE2nodeComponents)) OF ProtocolIE-SingleContainer { {E2nodeComponentConfigRemovalAck-ItemIEs} }
E2nodeComponentConfigRemovalAck-ItemIEs E2AP-PROTOCOL-IES ::= {
{ ID id-E2nodeComponentConfigRemovalAck-Item CRITICALITY reject TYPE
E2nodeComponentConfigRemovalAck-Item PRESENCE mandatory },
...
}
E2nodeComponentConfigRemovalAck-Item ::= SEQUENCE {
e2nodeComponentInterfaceType E2nodeComponentInterfaceType,
e2nodeComponentID E2nodeComponentID,
e2nodeComponentConfigurationAck E2nodeComponentConfigurationAck,
...
}
-- **************************************************************
--
-- E2 NODE CONFIGURATION UPDATE FAILURE
--
-- **************************************************************
E2nodeConfigurationUpdateFailure ::= SEQUENCE {
protocolIEs ProtocolIE-Container {{E2nodeConfigurationUpdateFailure-IEs}},
...
}
E2nodeConfigurationUpdateFailure-IEs E2AP-PROTOCOL-IES ::= {
{ ID id-TransactionID CRITICALITY reject TYPE TransactionID
PRESENCE mandatory }|
{ ID id-Cause CRITICALITY ignore TYPE Cause
PRESENCE mandatory }|
{ ID id-TimeToWait CRITICALITY ignore TYPE TimeToWait
PRESENCE optional }|
{ ID id-CriticalityDiagnostics CRITICALITY ignore TYPE CriticalityDiagnostics
PRESENCE optional },
...
}
-- **************************************************************
--
-- Reset Elementary Procedure
--
-- **************************************************************
-- **************************************************************
--
-- RESET REQUEST
--
-- **************************************************************
ResetRequest ::= SEQUENCE {
protocolIEs ProtocolIE-Container { {ResetRequestIEs} },
...
}
ResetRequestIEs E2AP-PROTOCOL-IES ::= {
{ ID id-TransactionID CRITICALITY reject TYPE TransactionID PRESENCE
mandatory }|
{ ID id-Cause CRITICALITY ignore TYPE Cause PRESENCE
mandatory },
...
}
-- **************************************************************
--
-- RESET RESPONSE
--
-- **************************************************************
ResetResponse ::= SEQUENCE {
protocolIEs ProtocolIE-Container { {ResetResponseIEs} },
...
}
ResetResponseIEs E2AP-PROTOCOL-IES ::= {
{ ID id-TransactionID CRITICALITY reject TYPE TransactionID PRESENCE
mandatory }|
{ ID id-CriticalityDiagnostics CRITICALITY ignore TYPE CriticalityDiagnostics PRESENCE
optional },
...
}
-- **************************************************************
--
-- RIC Service Update Elementary Procedure
--
-- **************************************************************
-- **************************************************************
--
-- RIC SERVICE UPDATE
--
-- **************************************************************
RICserviceUpdate ::= SEQUENCE {
protocolIEs ProtocolIE-Container {{RICserviceUpdate-IEs}},
...
}
RICserviceUpdate-IEs E2AP-PROTOCOL-IES ::= {
{ ID id-TransactionID CRITICALITY reject TYPE TransactionID PRESENCE
mandatory }|
{ ID id-RANfunctionsAdded CRITICALITY reject TYPE RANfunctions-List PRESENCE
optional }|
{ ID id-RANfunctionsModified CRITICALITY reject TYPE RANfunctions-List PRESENCE
optional }|
{ ID id-RANfunctionsDeleted CRITICALITY reject TYPE RANfunctionsID-List PRESENCE
optional },
...
}
RANfunctions-List ::= SEQUENCE (SIZE(1..maxofRANfunctionID)) OF ProtocolIE-SingleContainer { {RANfunction-ItemIEs} }
RANfunction-ItemIEs E2AP-PROTOCOL-IES ::= {
{ ID id-RANfunction-Item CRITICALITY ignore TYPE RANfunction-Item PRESENCE
mandatory },
...
}
RANfunction-Item ::= SEQUENCE {
ranFunctionID RANfunctionID,
ranFunctionDefinition RANfunctionDefinition,
ranFunctionRevision RANfunctionRevision,
ranFunctionOID RANfunctionOID,
...
}
RANfunctionsID-List ::= SEQUENCE (SIZE(1..maxofRANfunctionID)) OF ProtocolIE-SingleContainer{{RANfunctionID-ItemIEs}}
RANfunctionID-ItemIEs E2AP-PROTOCOL-IES ::= {
{ ID id-RANfunctionID-Item CRITICALITY ignore TYPE RANfunctionID-Item PRESENCE
mandatory },
...
}
RANfunctionID-Item ::= SEQUENCE {
ranFunctionID RANfunctionID,
ranFunctionRevision RANfunctionRevision,
...
}
-- **************************************************************
-- RIC SERVICE UPDATE ACKNOWLEDGE
--
-- **************************************************************
RICserviceUpdateAcknowledge ::= SEQUENCE {
protocolIEs ProtocolIE-Container {{RICserviceUpdateAcknowledge-IEs}},
...
}
RICserviceUpdateAcknowledge-IEs E2AP-PROTOCOL-IES ::= {
{ ID id-TransactionID CRITICALITY reject TYPE TransactionID PRESENCE
mandatory }|
{ ID id-RANfunctionsAccepted CRITICALITY reject TYPE RANfunctionsID-List PRESENCE
optional }|
{ ID id-RANfunctionsRejected CRITICALITY reject TYPE RANfunctionsIDcause-List PRESENCE
optional },
...
}
RANfunctionsIDcause-List ::= SEQUENCE (SIZE(1..maxofRANfunctionID)) OF ProtocolIE-SingleContainer {
{RANfunctionIDcause-ItemIEs} }
RANfunctionIDcause-ItemIEs E2AP-PROTOCOL-IES ::= {
{ ID id-RANfunctionIEcause-Item CRITICALITY ignore TYPE RANfunctionIDcause-Item PRESENCE
mandatory },
...
}
RANfunctionIDcause-Item ::= SEQUENCE {
ranFunctionID RANfunctionID,
cause Cause,
...
}
-- **************************************************************
--
-- RIC SERVICE UPDATE FAILURE
--
-- **************************************************************
RICserviceUpdateFailure ::= SEQUENCE {
protocolIEs ProtocolIE-Container {{RICserviceUpdateFailure-IEs}},
...
}
RICserviceUpdateFailure-IEs E2AP-PROTOCOL-IES ::= {
{ ID id-TransactionID CRITICALITY reject TYPE TransactionID PRESENCE
mandatory }|
{ ID id-Cause CRITICALITY reject TYPE Cause PRESENCE
mandatory }|
{ ID id-TimeToWait CRITICALITY ignore TYPE TimeToWait PRESENCE
optional }|
{ ID id-CriticalityDiagnostics CRITICALITY ignore TYPE CriticalityDiagnostics PRESENCE
optional },
...
}
-- **************************************************************
--
-- RIC Service Query Elementary Procedure
--
-- **************************************************************
-- **************************************************************
--
-- RIC SERVICE QUERY
--
-- **************************************************************
RICserviceQuery ::= SEQUENCE {
protocolIEs ProtocolIE-Container {{RICserviceQuery-IEs}},
...
}
RICserviceQuery-IEs E2AP-PROTOCOL-IES ::= {
{ ID id-TransactionID CRITICALITY reject TYPE TransactionID PRESENCE
mandatory }|
{ ID id-RANfunctionsAccepted CRITICALITY reject TYPE RANfunctionsID-List PRESENCE
optional },
...
}
-- **************************************************************
--
-- E2 Removal Elementary Procedure
--
-- **************************************************************
-- **************************************************************
--
-- E2 REMOVAL REQUEST
--
-- **************************************************************
E2RemovalRequest ::= SEQUENCE {
protocolIEs ProtocolIE-Container { {E2RemovalRequestIEs} },
...
}
E2RemovalRequestIEs E2AP-PROTOCOL-IES ::= {
{ ID id-TransactionID CRITICALITY reject TYPE TransactionID PRESENCE
mandatory },
...
}
-- **************************************************************
--
-- E2 REMOVAL RESPONSE
--
-- **************************************************************
E2RemovalResponse ::= SEQUENCE {
protocolIEs ProtocolIE-Container { {E2RemovalResponseIEs} },
...
}
E2RemovalResponseIEs E2AP-PROTOCOL-IES ::= {
{ ID id-TransactionID CRITICALITY reject TYPE TransactionID
PRESENCE mandatory }|
{ ID id-CriticalityDiagnostics CRITICALITY ignore TYPE CriticalityDiagnostics PRESENCE
optional },
...
}
-- **************************************************************
--
-- E2 REMOVAL FAILURE
--
-- **************************************************************
E2RemovalFailure ::= SEQUENCE {
protocolIEs ProtocolIE-Container { {E2RemovalFailureIEs} },
...
}
E2RemovalFailureIEs E2AP-PROTOCOL-IES ::= {
{ ID id-TransactionID CRITICALITY reject TYPE TransactionID PRESENCE
mandatory }|
{ ID id-Cause CRITICALITY ignore TYPE Cause PRESENCE
mandatory }|
{ ID id-CriticalityDiagnostics CRITICALITY ignore TYPE CriticalityDiagnostics PRESENCE
optional },
...
}
END
-- ASN1STOP-- ASN1START
-- **************************************************************
--
-- Elementary Procedure definitions
-- Derived from 3GPP 38.413 NGAP
-- **************************************************************
E2AP-PDU-Descriptions {
  iso(1) identified-organization(3) dod(6) internet(1) private(4) enterprise(1) 53148 e2(1) version2 (2)
  e2ap(1) e2ap-PDU-Descriptions (0)
}
DEFINITIONS AUTOMATIC TAGS ::=
BEGIN

-- **************************************************************
--
-- IE parameter types from other modules.
--
-- **************************************************************
IMPORTS
  Criticality,
  ProcedureCode
FROM E2AP-CommonDataTypes

  E2connectionUpdate,
  E2connectionUpdateAcknowledge,
  E2connectionUpdateFailure,
  E2nodeConfigurationUpdate,
  E2nodeConfigurationUpdateAcknowledge,
  E2nodeConfigurationUpdateFailure,
  E2RemovalRequest,
  E2RemovalResponse,
  E2RemovalFailure,
  E2setupFailure,
  E2setupRequest,
  E2setupResponse,
  ErrorIndication,
  ResetRequest,
  ResetResponse,
  RICassistanceFailure,
  RICassistanceIndication,
  RICassistanceHalt,
  RICassistanceRequest,
  RICassistanceResponse,
  RICcontrolAcknowledge,
  RICcontrolFailure,
  RICcontrolRequest,
  RICindication,
  RICserviceLoadStatusRequest,
  RICserviceLoadStatusResponse,
  RICserviceLoadStatusFailure,
  RICserviceLoadUpdate,
  RICserviceQuery,
  RICserviceUpdate,
  RICserviceUpdateAcknowledge,
  RICserviceUpdateFailure,
  RICsubscriptionFailure,
  RICsubscriptionRequest,
  RICsubscriptionResponse,
  RICsubscriptionAuditFailure,
  RICsubscriptionAuditRequest,
  RICsubscriptionAuditResponse,
  RICsubscriptionDeleteFailure,
  RICsubscriptionDeleteRequest,
  RICsubscriptionDeleteResponse,
  RICsubscriptionDeleteRequired,
  RICsubscriptionModificationRequest,
  RICsubscriptionModificationResponse,
  RICsubscriptionModificationFailure,
  RICsubscriptionModificationRequired,
  RICsubscriptionModificationConfirm,
  RICsubscriptionModificationRefuse,
  RICsubscriptionStateControlRequest,
  RICsubscriptionStateControlResponse,
  RICsubscriptionStateControlFailure,
  RICqueryRequest,
  RICqueryResponse,
  RICqueryFailure
FROM E2AP-PDU-Contents

  id-E2setup,
  id-ErrorIndication,
  id-Reset,
  id-RICcontrol,
  id-RICindication,
  id-RICserviceQuery,
  id-RICserviceUpdate,
  id-RICsubscription,
  id-RICsubscriptionDelete,
  id-E2nodeConfigurationUpdate,
  id-E2connectionUpdate,
  id-RICsubscriptionDeleteRequired,
  id-E2removal,
  id-RICsubscriptionModification,
  id-RICsubscriptionModificationRequired,
  id-RICquery,
  id-RICsubscriptionAudit,
  id-RICserviceLoadStatus,
  id-RICserviceLoadUpdate,
  id-RICsubscriptionStateControl,
  id-RICassistance,
  id-RICassistanceIndication,
  id-RICassistanceHalt
FROM E2AP-Constants;

-- **************************************************************
--
-- Interface Elementary Procedure Class
--
-- **************************************************************
E2AP-ELEMENTARY-PROCEDURE ::= CLASS {
  &InitiatingMessage,
  &SuccessfulOutcome      OPTIONAL,
  &UnsuccessfulOutcome    OPTIONAL,
  &procedureCode          ProcedureCode UNIQUE,
  &criticality            Criticality DEFAULT ignore
}
WITH SYNTAX {
  INITIATING MESSAGE      &InitiatingMessage
  [SUCCESSFUL OUTCOME     &SuccessfulOutcome]
  [UNSUCCESSFUL OUTCOME   &UnsuccessfulOutcome]
  PROCEDURE CODE          &procedureCode
  [CRITICALITY            &criticality]
}

-- **************************************************************
--
-- Interface PDU Definition
--
-- **************************************************************
E2AP-PDU ::= CHOICE {
  initiatingMessage   InitiatingMessage,
  successfulOutcome   SuccessfulOutcome,
  unsuccessfulOutcome UnsuccessfulOutcome,
  ...
}

InitiatingMessage ::= SEQUENCE {
  procedureCode  E2AP-ELEMENTARY-PROCEDURE.&procedureCode ({E2AP-ELEMENTARY-PROCEDURES}),
  criticality    E2AP-ELEMENTARY-PROCEDURE.&criticality ({E2AP-ELEMENTARY-PROCEDURES}{@procedureCode}),
  value          E2AP-ELEMENTARY-PROCEDURE.&InitiatingMessage ({E2AP-ELEMENTARY-PROCEDURES}{@procedureCode})
}

SuccessfulOutcome ::= SEQUENCE {
  procedureCode  E2AP-ELEMENTARY-PROCEDURE.&procedureCode ({E2AP-ELEMENTARY-PROCEDURES}),
  criticality    E2AP-ELEMENTARY-PROCEDURE.&criticality ({E2AP-ELEMENTARY-PROCEDURES}{@procedureCode}),
  value          E2AP-ELEMENTARY-PROCEDURE.&SuccessfulOutcome ({E2AP-ELEMENTARY-PROCEDURES}{@procedureCode})
}

UnsuccessfulOutcome ::= SEQUENCE {
  procedureCode  E2AP-ELEMENTARY-PROCEDURE.&procedureCode ({E2AP-ELEMENTARY-PROCEDURES}),
  criticality    E2AP-ELEMENTARY-PROCEDURE.&criticality ({E2AP-ELEMENTARY-PROCEDURES}{@procedureCode}),
  value          E2AP-ELEMENTARY-PROCEDURE.&UnsuccessfulOutcome ({E2AP-ELEMENTARY-PROCEDURES}{@procedureCode})
}

-- **************************************************************
--
-- Interface Elementary Procedure List
--
-- **************************************************************
E2AP-ELEMENTARY-PROCEDURES E2AP-ELEMENTARY-PROCEDURE ::= {
  E2AP-ELEMENTARY-PROCEDURES-CLASS-1 |
  E2AP-ELEMENTARY-PROCEDURES-CLASS-2,
  ...
}

E2AP-ELEMENTARY-PROCEDURES-CLASS-1 E2AP-ELEMENTARY-PROCEDURE ::= {
  ricSubscription |
  ricSubscriptionAudit |
  ricSubscriptionDelete |
  ricSubscriptionModification |
  ricSubscriptionModificationRequired |
  ricSubscriptionStateControl |
  ricQuery |
  ricServiceUpdate |
  ricAssistance |
  ricControl |
  ricServiceLoadStatus |
  e2setup |
  e2nodeConfigurationUpdate |
  e2connectionUpdate |
  reset |
  e2removal,
  ...
}

E2AP-ELEMENTARY-PROCEDURES-CLASS-2 E2AP-ELEMENTARY-PROCEDURE ::= {
  ricAssistanceIndication |
  ricAssistanceHalt |
  ricIndication |
  ricServiceQuery |
  ricServiceLoadUpdate |
  errorIndication |
  ricSubscriptionDeleteRequired,
  ...
}

-- **************************************************************
--
-- Interface Elementary Procedures
--
-- **************************************************************
-- New for v01.01
e2connectionUpdate E2AP-ELEMENTARY-PROCEDURE ::= {
  INITIATING MESSAGE    E2connectionUpdate
  SUCCESSFUL OUTCOME    E2connectionUpdateAcknowledge
  UNSUCCESSFUL OUTCOME  E2connectionUpdateFailure
  PROCEDURE CODE        id-E2connectionUpdate
  CRITICALITY           reject
}

e2nodeConfigurationUpdate E2AP-ELEMENTARY-PROCEDURE ::= {
  INITIATING MESSAGE    E2nodeConfigurationUpdate
  SUCCESSFUL OUTCOME    E2nodeConfigurationUpdateAcknowledge
  UNSUCCESSFUL OUTCOME  E2nodeConfigurationUpdateFailure
  PROCEDURE CODE        id-E2nodeConfigurationUpdate
  CRITICALITY           reject
}

-- New for v02.01
e2removal E2AP-ELEMENTARY-PROCEDURE ::= {
  INITIATING MESSAGE    E2RemovalRequest
  SUCCESSFUL OUTCOME    E2RemovalResponse
  UNSUCCESSFUL OUTCOME  E2RemovalFailure
  PROCEDURE CODE        id-E2removal
  CRITICALITY           reject
}

e2setup E2AP-ELEMENTARY-PROCEDURE ::= {
  INITIATING MESSAGE    E2setupRequest
  SUCCESSFUL OUTCOME    E2setupResponse
  UNSUCCESSFUL OUTCOME  E2setupFailure
  PROCEDURE CODE        id-E2setup
  CRITICALITY           reject
}

errorIndication E2AP-ELEMENTARY-PROCEDURE ::= {
  INITIATING MESSAGE    ErrorIndication
  PROCEDURE CODE        id-ErrorIndication
  CRITICALITY           ignore
}

reset E2AP-ELEMENTARY-PROCEDURE ::= {
  INITIATING MESSAGE    ResetRequest
  SUCCESSFUL OUTCOME    ResetResponse
  PROCEDURE CODE        id-Reset
  CRITICALITY           reject
}

ricAssistance E2AP-ELEMENTARY-PROCEDURE ::= {
  INITIATING MESSAGE    RICassistanceRequest
  SUCCESSFUL OUTCOME    RICassistanceResponse
  UNSUCCESSFUL OUTCOME  RICassistanceFailure
  PROCEDURE CODE        id-RICassistance
  CRITICALITY           reject
}

ricAssistanceIndication E2AP-ELEMENTARY-PROCEDURE ::= {
  INITIATING MESSAGE    RICassistanceIndication
  PROCEDURE CODE        id-RICassistanceIndication
  CRITICALITY           reject
}

ricAssistanceHalt E2AP-ELEMENTARY-PROCEDURE ::= {
  INITIATING MESSAGE    RICassistanceHalt
  PROCEDURE CODE        id-RICassistanceHalt
  CRITICALITY           reject
}

ricControl E2AP-ELEMENTARY-PROCEDURE ::= {
  INITIATING MESSAGE    RICcontrolRequest
  SUCCESSFUL OUTCOME    RICcontrolAcknowledge
  UNSUCCESSFUL OUTCOME  RICcontrolFailure
  PROCEDURE CODE        id-RICcontrol
  CRITICALITY           reject
}

ricIndication E2AP-ELEMENTARY-PROCEDURE ::= {
  INITIATING MESSAGE    RICindication
  PROCEDURE CODE        id-RICindication
  CRITICALITY           ignore
}

ricServiceLoadStatus E2AP-ELEMENTARY-PROCEDURE ::= {
  INITIATING MESSAGE    RICserviceLoadStatusRequest
  SUCCESSFUL OUTCOME    RICserviceLoadStatusResponse
  UNSUCCESSFUL OUTCOME  RICserviceLoadStatusFailure
  PROCEDURE CODE        id-RICserviceLoadStatus
  CRITICALITY           ignore
}

ricServiceLoadUpdate E2AP-ELEMENTARY-PROCEDURE ::= {
  INITIATING MESSAGE    RICserviceLoadUpdate
  PROCEDURE CODE        id-RICserviceLoadUpdate
  CRITICALITY           ignore
}

ricServiceQuery E2AP-ELEMENTARY-PROCEDURE ::= {
  INITIATING MESSAGE    RICserviceQuery
  PROCEDURE CODE        id-RICserviceQuery
  CRITICALITY           ignore
}

ricServiceUpdate E2AP-ELEMENTARY-PROCEDURE ::= {
  INITIATING MESSAGE    RICserviceUpdate
  SUCCESSFUL OUTCOME    RICserviceUpdateAcknowledge
  UNSUCCESSFUL OUTCOME  RICserviceUpdateFailure
  PROCEDURE CODE        id-RICserviceUpdate
  CRITICALITY           reject
}

ricSubscription E2AP-ELEMENTARY-PROCEDURE ::= {
  INITIATING MESSAGE    RICsubscriptionRequest
  SUCCESSFUL OUTCOME    RICsubscriptionResponse
  UNSUCCESSFUL OUTCOME  RICsubscriptionFailure
  PROCEDURE CODE        id-RICsubscription
  CRITICALITY           reject
}

ricSubscriptionAudit E2AP-ELEMENTARY-PROCEDURE ::= {
  INITIATING MESSAGE    RICsubscriptionAuditRequest
  SUCCESSFUL OUTCOME    RICsubscriptionAuditResponse
  UNSUCCESSFUL OUTCOME  RICsubscriptionAuditFailure
  PROCEDURE CODE        id-RICsubscriptionAudit
  CRITICALITY           reject
}

ricSubscriptionDelete E2AP-ELEMENTARY-PROCEDURE ::= {
  INITIATING MESSAGE    RICsubscriptionDeleteRequest
  SUCCESSFUL OUTCOME    RICsubscriptionDeleteResponse
  UNSUCCESSFUL OUTCOME  RICsubscriptionDeleteFailure
  PROCEDURE CODE        id-RICsubscriptionDelete
  CRITICALITY           reject
}

ricSubscriptionDeleteRequired E2AP-ELEMENTARY-PROCEDURE ::= {
  INITIATING MESSAGE    RICsubscriptionDeleteRequired
  PROCEDURE CODE        id-RICsubscriptionDeleteRequired
  CRITICALITY           ignore
}

ricSubscriptionModification E2AP-ELEMENTARY-PROCEDURE ::= {
  INITIATING MESSAGE    RICsubscriptionModificationRequest
  SUCCESSFUL OUTCOME    RICsubscriptionModificationResponse
  UNSUCCESSFUL OUTCOME  RICsubscriptionModificationFailure
  PROCEDURE CODE        id-RICsubscriptionModification
  CRITICALITY           reject
}

ricSubscriptionModificationRequired E2AP-ELEMENTARY-PROCEDURE ::= {
  INITIATING MESSAGE    RICsubscriptionModificationRequired
  SUCCESSFUL OUTCOME    RICsubscriptionModificationConfirm
  UNSUCCESSFUL OUTCOME  RICsubscriptionModificationRefuse
  PROCEDURE CODE        id-RICsubscriptionModificationRequired
  CRITICALITY           reject
}

ricSubscriptionStateControl E2AP-ELEMENTARY-PROCEDURE ::= {
  INITIATING MESSAGE    RICsubscriptionStateControlRequest
  SUCCESSFUL OUTCOME    RICsubscriptionStateControlResponse
  UNSUCCESSFUL OUTCOME  RICsubscriptionStateControlFailure
  PROCEDURE CODE        id-RICsubscriptionStateControl
  CRITICALITY           reject
}

ricQuery E2AP-ELEMENTARY-PROCEDURE ::= {
  INITIATING MESSAGE    RICqueryRequest
  SUCCESSFUL OUTCOME    RICqueryResponse
  UNSUCCESSFUL OUTCOME  RICqueryFailure
  PROCEDURE CODE        id-RICquery
  CRITICALITY           reject
}

END
-- ASN1STOP
